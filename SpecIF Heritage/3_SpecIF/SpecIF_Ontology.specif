# SpecIF Ontology
An ontology for the Specification Integration Facility (SpecIF).
- Rights: Creative Commons 4.0 CC BY-SA, https://creativecommons.org/licenses/by-sa/4.0/

## SpecIF Ontology (SpecIF:Heading)
- dcterms:type: W3C:Ontology

## Introduction (SpecIF:Heading)
- dcterms:description: The SpecIF Ontology (Vocabulary) collects terms used in the domain of systems engineering and requirements management. Agreed-upon terms help both collaborators to communicate more clearly and systems to match data fields automatically. SpecIF adopts terms and their definitions from other initiatives, for example from the Dublin Core Metadata Initiative (DCMI), the Open Services for Lifecycle Collaboration (OSLC), the International Requirements Engineering Board (IREB) and the ProSTEP iViP association to be used in ReqIF data.
  All terms carry a namespace, which is the first part separated with ':' or '.' ― they are thus easily recognized in text and data fields. For display, systems may choose to replace the ontology terms by domain or language specific words. This collection itself is structured according to SpecIF using the ontology defined here. For example, the term descriptions are recognized as such, because they are tagged with '[[dcterms:description]]'.
  The terms have a lifecycle status as follows:
  - experimental: The term is being used in first projects, but has not yet any normative maturity.
  - submitted: The term has been submitted for adoption.
  - released: The term has been adopted for use with SpecIF and is preferred among equivalent terms.
  - equivalent: The term has been adopted for use with SpecIF, but the released term is preferred.
  - deprecated: The term shall not any more be used with SpecIF; use a released term.
  The Specification Interchange Facility (SpecIF) is the result of an initiative by the Gesellschaft für Systems Engineering (GfSE), the German chapter of The International Council on Systems Engineering (INCOSE).
  All information provided here is made available according to Creative Commons 4.0 CC BY-SA or the license chosen by the respective publishers. We appreciate any contribution or proposal; please contact Dr. Oskar von Dungern.
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
## Namespaces (SpecIF:Heading)
- dcterms:description: A 'Namespace' is a is a set of signs (names) that are used to identify and refer to objects of various kinds. A namespace ensures that all of a given set of objects have unique names so that they can be easily identified. (Source: Wikipedia)

## rdf: (SpecIF:Namespace)
- SpecIF:Origin: http://www.w3.org/1999/02/22-rdf-syntax-ns#

## rdfs: (SpecIF:Namespace)
- SpecIF:Origin: http://www.w3.org/2000/01/rdf-schema#

## owl: (SpecIF:Namespace)
- SpecIF:Origin: http://www.w3.org/2002/07/owl#

## W3C: (SpecIF:Namespace)
- dcterms:description: The World Wide Web Consortium (W3C) is the main international standards organization for the World Wide Web. Founded in 1994 and led by Tim Berners-Lee, the consortium is made up of member organizations that maintain full-time staff working together in the development of standards for the World Wide Web. W3C also engages in education and outreach, develops software and serves as an open forum for discussion about the Web. *(Source: [Wikipedia](https://en.wikipedia.org/wiki/World_Wide_Web_Consortium))*
- SpecIF:Origin: https://www.w3.org/standards/semanticweb#

## xs: (SpecIF:Namespace)
- SpecIF:Origin: http://www.w3.org/2001/XMLSchema#

## xsd: (SpecIF:Namespace)
- SpecIF:Origin: http://www.w3.org/2001/XMLSchema#

## dcterms: (SpecIF:Namespace)
- SpecIF:Origin: http://purl.org/dc/terms/

## dc: (SpecIF:Namespace)
- SpecIF:Origin: http://purl.org/dc/elements/1.1/

## schema: (SpecIF:Namespace)
- dcterms:description: 'Schema.org' is a collaborative, community activity with a mission to create, maintain, and promote schemas for structured data on the Internet, on web pages, in email messages, and beyond.
- SpecIF:Origin: https://schema.org#

## iana: (SpecIF:Namespace)
- dcterms:description: Alternative origin: http://www.w3.org/ns/iana/media-types/
- SpecIF:Origin: https://www.iana.org/assignments/media-types#

## foaf: (SpecIF:Namespace)
- SpecIF:Origin: http://xmlns.com/foaf/0.1/

## FMC: (SpecIF:Namespace)
- dcterms:description: FMC is the acronym for "Fundamental Modeling Concepts", primarily a consistent and coherent way to think and talk about dynamic systems. It enables people to communicate the concepts and structures of complex informational systems in an efficient way among the different types of stakeholders. *(Source: [What is FMC?](http://www.fmc-modeling.org/quick-intro))*
- SpecIF:Origin: http://fmc-modeling.org#

## IR: (SpecIF:Namespace)
- dcterms:description: Interaction Room Workshop Method
- SpecIF:Origin: https://www.adesso.de/de/impulse/interaction-room/index.jsp#

## IREB: (SpecIF:Namespace)
- dcterms:description: Alternative origin: https://www.ireb.org/de/cpre/glossary/
- SpecIF:Origin: https://www.ireb.org/en/downloads/#cpre-glossary

## ReqIF. (SpecIF:Namespace)
- SpecIF:Origin: https://www.prostep.org/fileadmin/downloads/PSI_ImplementationGuide_ReqIF_V1-7.pdf#

## ReqIF-WF. (SpecIF:Namespace)
- SpecIF:Origin: https://www.prostep.org/fileadmin/downloads/Recommendation_ReqIF_V2_RZ3.pdf#

## HIS: (SpecIF:Namespace)
- SpecIF:Origin: https://www.itwissen.info/Herstellerinitiative-Software-Automotive-HIS.html#

## oslc: (SpecIF:Namespace)
- SpecIF:Origin: http://open-services.net/ns/core#

## oslc_rm: (SpecIF:Namespace)
- dcterms:description: Open Services for Lifecycle Collaboration (OSLC) - Requirement Management
- SpecIF:Origin: http://open-services.net/ns/rm#

## oslc_cm: (SpecIF:Namespace)
- dcterms:description: Open Services for Lifecycle Collaboration (OSLC) - Change Management
- SpecIF:Origin: http://open-services.net/ns/cm#

## ArchiMate: (SpecIF:Namespace)
- dcterms:description: ArchiMate is an open and independent enterprise architecture modeling language to support the description, analysis and visualization of architecture within and across business domains[1] in an unambiguous way.  ArchiMate is a technical standard from The Open Group and is based on concepts from the now superseded IEEE 1471 standard. It is supported by various tool vendors and consulting firms. ArchiMate is also a registered trademark of The Open Group. The Open Group has a certification program for ArchiMate users, software tools and courses.  *(Source: [Wikipedia](https://en.wikipedia.org/wiki/ArchiMate))*
- SpecIF:Origin: https://pubs.opengroup.org#

## bpmn: (SpecIF:Namespace)
- SpecIF:Origin: https://www.bpmn.org/#

## uml: (SpecIF:Namespace)
- SpecIF:Origin: https://www.omg.org/spec/UML#

## sysml: (SpecIF:Namespace)
- SpecIF:Origin: https://www.omg.org/spec/SysML#

## pig: (SpecIF:Namespace)
- dcterms:description: The 'Product Information Graph' as developed by project [CASCaDE](https://cascade.gfse.org) for submission of a standard supporting collaboration in the lifecycle.of mechatronic products.
- SpecIF:Origin: https://cascade.gfse.org/results#

## DDP: (SpecIF:Namespace)
- dcterms:description: Digital Data Package defined by prostep IVIP e.V.: https://www.prostep.org/projekte/digital-data-package-ddp
- SpecIF:Origin: http://www.prostep.org/dictionary/2.0#

## SpecIF: (SpecIF:Namespace)
- dcterms:description: The Specification Integration Facility (SpecIF) integrates partial system models from different methods and tools in a semantic net. Collaborators shall browse, search and audit engineering results in a common context. Also, the exchange of model information between organizations and tools is facilitated. SpecIF represents the visible, i.e. the diagrams and the text, as well as the semantics of system specifications.
- SpecIF:Origin: https://specif.de/v1.1/schema#

## Resource Class Terms (SpecIF:Heading)
- dcterms:description: A resource represents an artefact, e.g. a model element or a requirement. The terms listed in this chapter may be used to distinguish different classes (types) of artefacts constituting a system specification. A resource may serve as subject or as object in a subject-predicate-object statement. Each resource class may define an individual set of properties for carrying the information 'payload'.
  A resource class corresponds to a 'SPEC-OBJECT-TYPE' and a resource is a 'SPEC-OBJECT' in the Requirements Interchange Format (ReqIF). In ArchiMate® 3.0, a resource is an Element.

## SpecIF:Paragraph (SpecIF:TermResourceClass)
- dcterms:identifier: RC-Paragraph
- SpecIF:Revision: 1.1
- dcterms:description: A 'Paragraph' is an unspecified information in a document at any level.
- SpecIF:Domain: SpecIF:DomainBase, SpecIF:DomainRequirementsEngineering, SpecIF:DomainRequirementsEngineeringSRC, SpecIF:DomainSystemModelIntegration
- SpecIF:TermStatus: SpecIF:LifecycleStatusReleased
- SpecIF:LocalTerm: Paragraph
- SpecIF:LocalTermPlural: Paragraphs
- SpecIF:isHeading: false
- SpecIF:Instantiation: auto, user

## SpecIF:Information (SpecIF:TermResourceClass)
- dcterms:description: A 'Paragraph' is an unspecified information in a document at any level.
- SpecIF:Domain: SpecIF:DomainBase
- SpecIF:TermStatus: SpecIF:LifecycleStatusDeprecated
- SpecIF:LocalTerm: Information
- SpecIF:LocalTermPlural: Informations
- SpecIF:isHeading: false
- SpecIF:Instantiation: auto, user

## SpecIF:Heading (SpecIF:TermResourceClass)
- dcterms:identifier: RC-Folder
- SpecIF:Revision: 1.1
- dcterms:description: A 'Heading' is a chapter title at any level with optional description.
- SpecIF:Domain: SpecIF:DomainBase, SpecIF:DomainRequirementsEngineering, SpecIF:DomainRequirementsEngineeringSRC, SpecIF:DomainSystemModelIntegration, SpecIF:DomainOntology
- SpecIF:TermStatus: SpecIF:LifecycleStatusReleased
- SpecIF:LocalTerm: Heading, Chapter Title
- SpecIF:LocalTermPlural: Headings
- SpecIF:isHeading: true
- SpecIF:Instantiation: auto, user

## SpecIF:Folder (SpecIF:TermResourceClass)
- dcterms:description: A 'Folder' may appear at any level with optional description.
- SpecIF:TermStatus: SpecIF:LifecycleStatusDeprecated
- SpecIF:LocalTerm: Folder
- SpecIF:LocalTermPlural: Folders
- SpecIF:isHeading: true
- SpecIF:Instantiation: auto, user

## SpecIF:View (SpecIF:TermResourceClass)
- SpecIF:Revision: 1.2
- dcterms:description: A 'Model View' is a graphical diagram with a specific communication purpose, e.g. a business process or system composition. A suitable notation is applied.
- SpecIF:Domain: SpecIF:DomainSystemsEngineering, SpecIF:DomainSystemModelIntegration
- SpecIF:TermStatus: SpecIF:LifecycleStatusReleased
- SpecIF:LocalTerm: Model Diagram, Diagram, Plan, Diagram, Plan
- SpecIF:Icon: ▣
- SpecIF:isHeading: false
- SpecIF:Instantiation: auto, user

## uml:Diagram (SpecIF:TermResourceClass)
- SpecIF:Revision: 1.2
- dcterms:description: A 'Diagram' is a graphical model view with a specific communication purpose, e.g. a business process or system composition.
- SpecIF:Domain: SpecIF:DomainSystemsEngineering, SpecIF:DomainSystemModelIntegration
- SpecIF:TermStatus: SpecIF:LifecycleStatusEquivalent
- SpecIF:LocalTerm: Model Diagram
- SpecIF:LocalTermPlural: Model Diagrams
- SpecIF:isHeading: false
- SpecIF:Instantiation: auto

## SpecIF:Views (SpecIF:TermResourceClass)
- SpecIF:Revision: 1.2
- SpecIF:TermStatus: SpecIF:LifecycleStatusReleased
- SpecIF:LocalTerm: Model Diagrams, Diagrams, Plans
- SpecIF:Icon: ▣
- SpecIF:isHeading: false
- SpecIF:Instantiation: auto

## ArchiMate:Viewpoint (SpecIF:TermResourceClass)
- SpecIF:Revision: 1.2
- SpecIF:LocalTerm: Model Diagram
- SpecIF:LocalTermPlural: Model Diagrams
- dcterms:description: A viewpoint in the ArchiMate language is a selection of a relevant subset of the ArchiMate elements and their relationships. This is the representation of that part of an architecture that is expressed in different diagrams.
- SpecIF:TermStatus: SpecIF:LifecycleStatusEquivalent
- SpecIF:Icon: ▣
- SpecIF:isHeading: false
- SpecIF:Instantiation: auto

## SpecIF:Diagram (SpecIF:TermResourceClass)
- dcterms:description: A 'Diagram' is a graphical model view with a specific communication purpose, e.g. a business process or system composition.
- SpecIF:TermStatus: SpecIF:LifecycleStatusDeprecated
- SpecIF:LocalTerm: Model Diagram
- SpecIF:LocalTermPlural: Model Diagrams
- SpecIF:isHeading: false

## IREB:Requirement (SpecIF:TermResourceClass)
- dcterms:identifier: RC-Requirement
- SpecIF:Revision: 1.2
- dcterms:description: A 'Requirement' is a singular documented physical and functional need that a particular design, product or process must be able to perform. (source: Wikipedia)
  Definition:
  1. A condition or capability needed by a user to solve a problem or achieve an objective.
  2. A condition or capability that must be met or possessed by a system or system component to satisfy a contract, standard, specification, or other formally imposed documents.
  3. A documented representation of a condition or capability as in (1) or (2).
  Note: The definition above is the classic one from IEEE Std 610.12 of 1990. Alternatively, we also give a more modern definition:
  1. A need perceived by a stakeholder.
  2. A capability or property that a system shall have.
  3. A documented representation of a need, capability or property.
- SpecIF:LocalTerm: Requirement
- SpecIF:LocalTermPlural: Requirements
- SpecIF:Domain: SpecIF:DomainRequirementsEngineering, SpecIF:DomainRequirementsEngineeringSRC, SpecIF:DomainSystemModelIntegration
- SpecIF:TermStatus: SpecIF:LifecycleStatusReleased
- SpecIF:Icon: ↯
- SpecIF:isHeading: false
- SpecIF:Instantiation: user

## SpecIF:Requirement (SpecIF:TermResourceClass)
- dcterms:identifier: RC-Requirement
- dcterms:description: A 'Requirement' is a singular documented physical and functional need that a particular design, product or process must be able to perform. (source: Wikipedia)
  Definition:
  1. A condition or capability needed by a user to solve a problem or achieve an objective.
  2. A condition or capability that must be met or possessed by a system or system component to satisfy a contract, standard, specification, or other formally imposed documents.
  3. A documented representation of a condition or capability as in (1) or (2).
  Note: The definition above is the classic one from IEEE Std 610.12 of 1990. Alternatively, we also give a more modern definition:
  1. A need perceived by a stakeholder.
  2. A capability or property that a system shall have.
  3. A documented representation of a need, capability or property.
- SpecIF:TermStatus: SpecIF:LifecycleStatusDeprecated
- SpecIF:LocalTerm: Requirement
- SpecIF:LocalTermPlural: Requirements
- SpecIF:Icon: ❢
- SpecIF:isHeading: false
- SpecIF:Instantiation: user

## ReqIF-WF.Requirement (SpecIF:TermResourceClass)
- SpecIF:Revision: 1.2
- dcterms:description: A 'Requirement' is a singular documented physical and functional need that a particular design, product or process must be able to perform. (source: Wikipedia)
  Definition:
  1. A condition or capability needed by a user to solve a problem or achieve an objective.
  2. A condition or capability that must be met or possessed by a system or system component to satisfy a contract, standard, specification, or other formally imposed documents.
  3. A documented representation of a condition or capability as in (1) or (2).
  Note: The definition above is the classic one from IEEE Std 610.12 of 1990. Alternatively, we also give a more modern definition:
  1. A need perceived by a stakeholder.
  2. A capability or property that a system shall have.
  3. A documented representation of a need, capability or property.
- SpecIF:Domain: SpecIF:DomainRequirementsEngineeringSRC
- SpecIF:TermStatus: SpecIF:LifecycleStatusReleased
- SpecIF:LocalTerm: Requirement
- SpecIF:LocalTermPlural: Requirements
- SpecIF:Icon: ❢
- SpecIF:isHeading: false
- SpecIF:Instantiation: user

## SpecIF:DesignDecision (SpecIF:TermResourceClass)
- SpecIF:Revision: 1.2
- dcterms:description: Characteristics:
  - Design decisions take into account human considerations, from ergonomics to cognitive capabilities. A good solution has to be useable and useful.
  - Design decisions have some sort of aesthetic component—that is: the beauty and elegance of the execution. This is true even if the solution has no physical component. A good solution has to be pleasurable.

  Source: [Dan Saffer: What is a Design Decision?](https://odannyboy.medium.com/what-is-a-design-decision-21fb7fb17089)
- SpecIF:Domain: SpecIF:DomainSystemsEngineering, SpecIF:DomainSystemModelIntegration
- SpecIF:TermStatus: SpecIF:LifecycleStatusSubmitted
- SpecIF:LocalTerm: Design Decision
- SpecIF:isHeading: false
- SpecIF:Instantiation: auto, user

## SpecIF:Namespace (SpecIF:TermResourceClass)
- SpecIF:Revision: 1.2
- dcterms:description: A 'Namespace' is a is a set of signs (names) that are used to identify and refer to objects of various kinds. A namespace ensures that all of a given set of objects have unique names so that they can be easily identified. (Source: Wikipedia)
- SpecIF:Domain: SpecIF:DomainOntology
- SpecIF:TermStatus: SpecIF:LifecycleStatusReleased
- SpecIF:LocalTerm: Namespace
- SpecIF:LocalTermPlural: Namespaces
- SpecIF:isHeading: false
- SpecIF:Instantiation: user

## SpecIF:Resource (SpecIF:TermResourceClass)
- dcterms:description: A **Node** is a vertex in a graph. Equivalent terms are entity, object and resource.
- SpecIF:Domain: SpecIF:DomainSystemModelIntegration
- SpecIF:TermStatus: SpecIF:LifecycleStatusSubmitted
- SpecIF:LocalTerm: Resource
- SpecIF:LocalTermPlural: Resources
- SpecIF:isHeading: false
- SpecIF:Instantiation: auto

## SpecIF:Statement (SpecIF:TermResourceClass)
- dcterms:description: An **Edge** connects 2 vertices in a graph. Equivalent terms are relationship, relation and statement.
- SpecIF:Domain: SpecIF:DomainSystemModelIntegration
- SpecIF:TermStatus: SpecIF:LifecycleStatusSubmitted
- SpecIF:LocalTerm: Statement
- SpecIF:LocalTermPlural: Statements
- SpecIF:isHeading: false
- SpecIF:Instantiation: auto

## SpecIF:Property (SpecIF:TermResourceClass)
- dcterms:description: A **Property** is a key-value pair associated with a node or edge. An equivalent term is attribute.
- SpecIF:Domain: SpecIF:DomainSystemModelIntegration
- SpecIF:TermStatus: SpecIF:LifecycleStatusSubmitted
- SpecIF:LocalTerm: Property
- SpecIF:LocalTermPlural: Properties
- SpecIF:isHeading: false
- SpecIF:Instantiation: auto

## FMC:Plan (SpecIF:TermResourceClass)
- dcterms:description: A 'Plan' is a graphical model view with a specific communication purpose, e.g. a business process or system composition.
- SpecIF:TermStatus: SpecIF:LifecycleStatusEquivalent
- SpecIF:LocalTerm: Plan
- SpecIF:LocalTermPlural: Plans
- SpecIF:isHeading: false

## SpecIF:ModelElement (SpecIF:TermResourceClass)
- SpecIF:Revision: 1.2
- dcterms:description: Is a generalized type for model elements.
- SpecIF:Domain: SpecIF:DomainSystemsEngineering, SpecIF:DomainSystemModelIntegration
- SpecIF:TermStatus: SpecIF:LifecycleStatusReleased
- SpecIF:LocalTerm: Model Element
- SpecIF:LocalTermPlural: Model Elements
- SpecIF:Icon: ☆
- SpecIF:isHeading: false
- SpecIF:Instantiation: auto

## uml:Class (SpecIF:TermResourceClass)
- SpecIF:Revision: 1.2
- dcterms:description: Is a generalized type for model elements.
- SpecIF:Domain: SpecIF:DomainSystemsEngineering, SpecIF:DomainSystemModelIntegration
- SpecIF:TermStatus: SpecIF:LifecycleStatusEquivalent
- SpecIF:LocalTerm: Class
- SpecIF:LocalTermPlural: Classes
- SpecIF:isHeading: false
- SpecIF:Instantiation: auto

## FMC:Actor (SpecIF:TermResourceClass)
- dcterms:identifier: RC-Actor
- SpecIF:Revision: 1.2
- dcterms:description: An 'Actor' is a fundamental model element type representing an active entity, be it an activity, a process step, a function, a system component or a role.
  The particular use or original type is specified with a [[dcterms:type]] property of the 'FMC:Actor'. A value of that property should be an ontology-term, such as [[bpmn:processStep]].
- SpecIF:Domain: SpecIF:DomainSystemModelIntegration
- SpecIF:TermStatus: SpecIF:LifecycleStatusReleased
- SpecIF:LocalTerm: Actor
- SpecIF:LocalTermPlural: Actors
- SpecIF:Icon: □
- SpecIF:isHeading: false
- SpecIF:Instantiation: auto

## FMC:State (SpecIF:TermResourceClass)
- dcterms:identifier: RC-State
- SpecIF:Revision: 1.2
- dcterms:description: A 'State' is a fundamental model element type representing a passive entity, be it a value, a condition, an information storage or even a physical shape.
  The particular use or the original type is specified with a [[dcterms:type]] property of the 'FMC:State'. A value of that property should bean ontology-term, such as [[bpmn:dataObject]].
- SpecIF:Domain: SpecIF:DomainSystemModelIntegration
- SpecIF:TermStatus: SpecIF:LifecycleStatusReleased
- SpecIF:LocalTerm: State
- SpecIF:LocalTermPlural: States
- SpecIF:Icon: ○
- SpecIF:isHeading: false
- SpecIF:Instantiation: auto

## FMC:Event (SpecIF:TermResourceClass)
- dcterms:identifier: RC-Event
- SpecIF:Revision: 1.2
- dcterms:description: An 'Event' is a fundamental model element type representing a time reference, a change in condition/value or more generally a synchronization primitive.
  The particular use or the original type is specified with a [[dcterms:type]] property of the 'FMC:Event'. A value of that property should be an ontology-term, such as [[bpmn:startEvent]].
- SpecIF:Domain: SpecIF:DomainSystemModelIntegration
- SpecIF:TermStatus: SpecIF:LifecycleStatusReleased
- SpecIF:LocalTerm: Event
- SpecIF:LocalTermPlural: Events
- SpecIF:Icon: ♢
- SpecIF:isHeading: false
- SpecIF:Instantiation: auto

## SpecIF:Collection (SpecIF:TermResourceClass)
- dcterms:identifier: RC-Collection
- SpecIF:Revision: 1.2
- dcterms:description: A 'Collection' is a logical (often conceptual) group of resources linked with a [[SpecIF:contains]] statement. It corresponds to a 'Group' in BPMN Diagrams.
  BPMN: An arbitrary set of objects can be defined as a Group to show that they logically belong together. (source: BPMN Tutorial)
- SpecIF:Domain: SpecIF:DomainSystemModelIntegration
- SpecIF:TermStatus: SpecIF:LifecycleStatusReleased
- SpecIF:LocalTerm: Collection or Group
- SpecIF:LocalTermPlural: Collections and Groups
- SpecIF:Icon: ⬚
- SpecIF:isHeading: false
- SpecIF:Instantiation: auto

## DDP:ProductFunction (SpecIF:TermResourceClass)
- SpecIF:Revision: 1.2
- dcterms:description: A product function describes the way a system works or performs a specific task.
- SpecIF:TermStatus: SpecIF:LifecycleStatusSubmitted
- SpecIF:LocalTerm: Product Function
- SpecIF:LocalTermPlural: Product Functions
- SpecIF:isHeading: false
- SpecIF:Instantiation: auto, user

## DDP:SystemComponent (SpecIF:TermResourceClass)
- SpecIF:Revision: 1.2
- dcterms:description: Represents a generic component of a system.
- SpecIF:TermStatus: SpecIF:LifecycleStatusSubmitted
- SpecIF:LocalTerm: System Component
- SpecIF:LocalTermPlural: System Components
- SpecIF:isHeading: false
- SpecIF:Instantiation: auto, user

## DDP:ComponentInterface (SpecIF:TermResourceClass)
- SpecIF:Revision: 1.2
- dcterms:description: Represents a generic interface of a system component.
- SpecIF:TermStatus: SpecIF:LifecycleStatusSubmitted
- SpecIF:LocalTerm: Component Interface
- SpecIF:LocalTermPlural: Component Interfaces
- SpecIF:isHeading: false
- SpecIF:Instantiation: auto, user

## bpmn:group (SpecIF:TermResourceClass)
- dcterms:description: BPMN: An arbitrary set of objects can be defined as a Group to show that they logically belong together. Like all BPMN 'artifacts', a group does not influence execution semantics. In PBMN, a group can be freely applied, even across pool boundaries. (source: BPMN Reference)
- SpecIF:TermStatus: SpecIF:LifecycleStatusExperimental

## SpecIF:Comment (SpecIF:TermResourceClass)
- dcterms:identifier: RC-Comment
- SpecIF:Revision: 1.1
- dcterms:description: A 'Comment' is reader feedback referring to a model element ('resource' or 'statement' in general).
- SpecIF:Domain: SpecIF:DomainBase, SpecIF:DomainRequirementsEngineering, SpecIF:DomainRequirementsEngineeringSRC, SpecIF:DomainSystemModelIntegration, SpecIF:DomainOntology
- SpecIF:TermStatus: SpecIF:LifecycleStatusReleased
- SpecIF:LocalTerm: Comment
- SpecIF:LocalTermPlural: Comments
- SpecIF:Icon: 🗅
- SpecIF:isHeading: false
- SpecIF:Instantiation: auto

## SpecIF:Note (SpecIF:TermResourceClass)
- dcterms:identifier: RC-Note
- SpecIF:Revision: 1.1
- dcterms:description: A 'Note' is additional information by the author referring to any resource.
- SpecIF:TermStatus: SpecIF:LifecycleStatusReleased
- SpecIF:LocalTerm: Note
- SpecIF:LocalTermPlural: Notes
- SpecIF:isHeading: false
- SpecIF:Instantiation: user

## SpecIF:Vote (SpecIF:TermResourceClass)
- dcterms:identifier: RC-Vote
- SpecIF:Revision: 1.2
- dcterms:description: A 'Vote' is an opinion referring to any resource or statement.
- SpecIF:TermStatus: SpecIF:LifecycleStatusReleased
- SpecIF:LocalTerm: Vote
- SpecIF:LocalTermPlural: Votes
- SpecIF:isHeading: false
- SpecIF:Instantiation: user

## IR:Annotation (SpecIF:TermResourceClass)
- dcterms:description: An Interaction-Room 'Annotation' indicates a point of special interest. Examples are customer or user value, product features with prominent benefit,effort or challenges during development.
- SpecIF:TermStatus: SpecIF:LifecycleStatusEquivalent
- SpecIF:LocalTerm: Annotation
- SpecIF:LocalTermPlural: Annotations
- SpecIF:Icon: ►
- SpecIF:isHeading: false
- SpecIF:Instantiation: user

## SpecIF:Issue (SpecIF:TermResourceClass)
- dcterms:description: An 'Issue' is a question to answer or decision to take which is worth tracking.
- SpecIF:Domain: SpecIF:DomainIssueManagement
- SpecIF:TermStatus: SpecIF:LifecycleStatusReleased
- SpecIF:LocalTerm: Open Issue
- SpecIF:LocalTermPlural: Open Issues
- SpecIF:isHeading: false
- SpecIF:Instantiation: user

## SpecIF:Permissions (SpecIF:TermResourceClass)
- SpecIF:Revision: 1.2
- dcterms:description: Permissions are a set of user rights, each allowing to use a certain function and/or to access a certain data set.
- SpecIF:Domain: SpecIF:DomainSystemModelIntegration
- SpecIF:TermStatus: SpecIF:LifecycleStatusReleased
- SpecIF:LocalTerm: Permission
- SpecIF:LocalTermPlural: Permissions
- SpecIF:isHeading: false
- SpecIF:Instantiation: user

## SpecIF:OntologyTerm (SpecIF:TermResourceClass)
- SpecIF:Revision: 1.2
- SpecIF:Domain: SpecIF:DomainOntology
- SpecIF:TermStatus: SpecIF:LifecycleStatusReleased
- SpecIF:LocalTerm: Term
- SpecIF:LocalTermPlural: Terms
- SpecIF:isHeading: false

## SpecIF:TermResourceClass (SpecIF:TermResourceClass)
- SpecIF:Revision: 1.1
- dcterms:description: A term for SpecIF resources, often used as title of a resourceClass to denote the class type.
- SpecIF:Domain: SpecIF:DomainOntology
- SpecIF:TermStatus: SpecIF:LifecycleStatusReleased
- SpecIF:LocalTerm: Noun
- SpecIF:LocalTermPlural: Nouns
- SpecIF:isHeading: false
- SpecIF:Instantiation: user

## SpecIF:TermStatementClass (SpecIF:TermResourceClass)
- SpecIF:Revision: 1.1
- dcterms:description: A term for SpecIF statements, often used as title of a statementClass to denote the class type.
- SpecIF:Domain: SpecIF:DomainOntology
- SpecIF:TermStatus: SpecIF:LifecycleStatusReleased
- SpecIF:LocalTerm: Verb
- SpecIF:LocalTermPlural: Verbs
- SpecIF:isHeading: false
- SpecIF:Instantiation: user

## SpecIF:TermPropertyClass (SpecIF:TermResourceClass)
- SpecIF:Revision: 1.1
- dcterms:description: Abstract parent class for property class terms belonging to the SpecIF Ontology.
- SpecIF:Domain: SpecIF:DomainOntology
- SpecIF:TermStatus: SpecIF:LifecycleStatusReleased
- SpecIF:LocalTerm: Property
- SpecIF:LocalTermPlural: Properties
- SpecIF:isHeading: false

## SpecIF:TermPropertyClassString (SpecIF:TermResourceClass)
- SpecIF:Revision: 1.1
- dcterms:description: A term for SpecIF properties with data type 'xs:string', often used as title of a propertyClass to denote the class type.
- SpecIF:Domain: SpecIF:DomainOntology
- SpecIF:TermStatus: SpecIF:LifecycleStatusReleased
- SpecIF:LocalTerm: Property (Text)
- SpecIF:LocalTermPlural: Properties (Text)
- SpecIF:isHeading: false
- SpecIF:Instantiation: user

## SpecIF:TermPropertyClassBoolean (SpecIF:TermResourceClass)
- SpecIF:Revision: 1.1
- dcterms:description: A term for SpecIF properties with data type 'xs:boolean', often used as title of a propertyClass to denote the class type.
- SpecIF:Domain: SpecIF:DomainOntology
- SpecIF:TermStatus: SpecIF:LifecycleStatusReleased
- SpecIF:LocalTerm: Property (Boolean)
- SpecIF:LocalTermPlural: Properties (Boolean)
- SpecIF:isHeading: false
- SpecIF:Instantiation: user

## SpecIF:TermPropertyClassInteger (SpecIF:TermResourceClass)
- SpecIF:Revision: 1.1
- dcterms:description: A term for SpecIF properties with data type 'xs:integer', often used as title of a propertyClass to denote the class type.
- SpecIF:Domain: SpecIF:DomainOntology
- SpecIF:TermStatus: SpecIF:LifecycleStatusReleased
- SpecIF:LocalTerm: Property (Integer)
- SpecIF:LocalTermPlural: Properties (Integer)
- SpecIF:isHeading: false
- SpecIF:Instantiation: user

## SpecIF:TermPropertyClassReal (SpecIF:TermResourceClass)
- SpecIF:Revision: 1.1
- dcterms:description: A term for SpecIF properties with data type 'xs:double', often used as title of a propertyClass to denote the class type.
- SpecIF:Domain: SpecIF:DomainOntology
- SpecIF:TermStatus: SpecIF:LifecycleStatusReleased
- SpecIF:LocalTerm: Property (Real)
- SpecIF:LocalTermPlural: Properties (Real)
- SpecIF:isHeading: false
- SpecIF:Instantiation: user

## SpecIF:TermPropertyClassTimestamp (SpecIF:TermResourceClass)
- SpecIF:Revision: 1.1
- dcterms:description: A term for SpecIF properties with data type 'xs:dateTime', often used as title of a propertyClass to denote the class type.
- SpecIF:Domain: SpecIF:DomainOntology
- SpecIF:TermStatus: SpecIF:LifecycleStatusReleased
- SpecIF:LocalTerm: Property (Timestamp)
- SpecIF:LocalTermPlural: Properties (Timestamp)
- SpecIF:isHeading: false
- SpecIF:Instantiation: user

## SpecIF:TermPropertyClassDuration (SpecIF:TermResourceClass)
- SpecIF:Revision: 1.1
- dcterms:description: A term for SpecIF properties with data type 'xs:duration', often used as title of a propertyClass to denote the class type.
- SpecIF:Domain: SpecIF:DomainOntology
- SpecIF:TermStatus: SpecIF:LifecycleStatusReleased
- SpecIF:LocalTerm: Property (Duration)
- SpecIF:LocalTermPlural: Properties (Duration)
- SpecIF:isHeading: false
- SpecIF:Instantiation: user

## SpecIF:TermPropertyClassURI (SpecIF:TermResourceClass)
- SpecIF:Revision: 1.1
- dcterms:description: A term for SpecIF properties with data type 'xs:anyURI', often used as title of a propertyClass to denote the class type.
- SpecIF:Domain: SpecIF:DomainOntology
- SpecIF:TermStatus: SpecIF:LifecycleStatusReleased
- SpecIF:LocalTerm: Property (URI)
- SpecIF:LocalTermPlural: Properties (URI)
- SpecIF:isHeading: false
- SpecIF:Instantiation: user

## SpecIF:TermPropertyValue (SpecIF:TermResourceClass)
- SpecIF:Revision: 1.1
- dcterms:description: A term for SpecIF property values, often used in enumerated dataTypes.
- SpecIF:Domain: SpecIF:DomainOntology
- SpecIF:TermStatus: SpecIF:LifecycleStatusReleased
- SpecIF:LocalTerm: Value
- SpecIF:LocalTermPlural: Values
- SpecIF:isHeading: false
- SpecIF:Instantiation: user

## IREB:Risk (SpecIF:TermResourceClass)
- dcterms:description: An event that threatens the success of an endeavor, e.g., of developing or operating a system. A risk is typically assessed in terms of its probability and potential damage.
- SpecIF:TermStatus: SpecIF:LifecycleStatusReleased
- SpecIF:LocalTerm: Risk
- SpecIF:isHeading: false
- SpecIF:Instantiation: user

## foaf:Person (SpecIF:TermResourceClass)
- dcterms:description: The Person class represents people. Something is a Person if it is a person. We don't nitpic about whether they're alive, dead, real, or imaginary. (source: FOAF)
- SpecIF:Domain: SpecIF:DomainRequirementsEngineering
- SpecIF:TermStatus: SpecIF:LifecycleStatusEquivalent
- SpecIF:isHeading: false
- SpecIF:Instantiation: user

## schema:Person (SpecIF:TermResourceClass)
- SpecIF:Revision: 1.2
- dcterms:description: A person (alive, dead, undead, or fictional).
- SpecIF:TermStatus: SpecIF:LifecycleStatusReleased
- SpecIF:LocalTerm: Person
- SpecIF:LocalTermPlural: Persons
- SpecIF:isHeading: false
- SpecIF:Instantiation: user

## schema:Role (SpecIF:TermResourceClass)
- SpecIF:Revision: 1.2
- dcterms:description: Represents additional information about a relationship or property. For example a Role can be used to say that a 'member' role linking some SportsTeam to a player occurred during a particular time period. Or that a Person's 'actor' role in a Movie was for some particular characterName. Such properties can be attached to a Role entity, which is then associated with the main entities using ordinary properties like 'member' or 'actor'.
- SpecIF:TermStatus: SpecIF:LifecycleStatusReleased
- SpecIF:LocalTerm: Role
- SpecIF:LocalTermPlural: Roles
- SpecIF:isHeading: false
- SpecIF:Instantiation: user

## schema:Organization (SpecIF:TermResourceClass)
- SpecIF:Revision: 1.2
- dcterms:description: An organization such as a school, NGO, corporation, club, etc.
- SpecIF:TermStatus: SpecIF:LifecycleStatusReleased
- SpecIF:LocalTerm: Organisation
- SpecIF:LocalTermPlural: Organisationen
- SpecIF:isHeading: false
- SpecIF:Instantiation: user

## SpecIF:HierarchyRoot (SpecIF:TermResourceClass)
- SpecIF:Revision: 1.2
- dcterms:description: A node (vertex) in a graph anchoring all instances of [[SpecIF:Hierarchy]].
- SpecIF:Domain: SpecIF:DomainBase, SpecIF:DomainRequirementsEngineering, SpecIF:DomainRequirementsEngineeringSRC, SpecIF:DomainSystemsEngineering, SpecIF:DomainSystemModelIntegration
- SpecIF:TermStatus: SpecIF:LifecycleStatusReleased
- SpecIF:LocalTerm: Hierarchy Root
- SpecIF:LocalTermPlural: Hierarchy Roots
- SpecIF:isHeading: false
- SpecIF:Instantiation: auto

## SpecIF:Hierarchy (SpecIF:TermResourceClass)
- dcterms:description: A tree-shaped structure with references to [[SpecIF:Resource]]s. Specializations are among others [[SpecIF:Outline]] (a document outline) and [[SpecIF:BillOfMaterials]]. While a graph does not have a start nor an end, a hierarchy gives easy access to relevant content depending on the target group or purpose.
- SpecIF:TermStatus: SpecIF:LifecycleStatusEquivalent
- SpecIF:isHeading: true

## SpecIF:Outline (SpecIF:TermResourceClass)
- SpecIF:Revision: 1.2
- dcterms:description: A root of a document structure with references to resources.
- SpecIF:TermStatus: SpecIF:LifecycleStatusReleased
- SpecIF:LocalTerm: Outline
- SpecIF:LocalTermPlural: Outlines
- SpecIF:isHeading: true
- SpecIF:Instantiation: user

## SpecIF:BillOfMaterials (SpecIF:TermResourceClass)
- SpecIF:Revision: 1.2
- dcterms:description: A bill of materials or product structure (sometimes bill of material, BOM or associated list) is a list of the raw materials, sub-assemblies, intermediate assemblies, sub-components, parts and the quantities of each needed to manufacture an end product. A BOM may be used for communication between manufacturing partners, or confined to a single manufacturing plant. (source: Wikipedia)
- SpecIF:Domain: SpecIF:DomainSystemModelIntegration
- SpecIF:TermStatus: SpecIF:LifecycleStatusReleased
- SpecIF:isHeading: true
- SpecIF:Instantiation: user

## SpecIF:BusinessProcess (SpecIF:TermResourceClass)
- SpecIF:Revision: 1.2
- SpecIF:Domain: SpecIF:DomainSystemModelIntegration
- SpecIF:TermStatus: SpecIF:LifecycleStatusEquivalent
- SpecIF:LocalTerm: Business Process
- SpecIF:isHeading: false
- SpecIF:Instantiation: auto

## SpecIF:BusinessProcesses (SpecIF:TermResourceClass)
- SpecIF:Revision: 1.2
- SpecIF:TermStatus: SpecIF:LifecycleStatusReleased
- SpecIF:LocalTerm: Business Processes
- SpecIF:isHeading: false
- SpecIF:Instantiation: auto

## SpecIF:Glossary (SpecIF:TermResourceClass)
- SpecIF:Revision: 1.2
- SpecIF:Domain: SpecIF:DomainSystemModelIntegration
- SpecIF:TermStatus: SpecIF:LifecycleStatusReleased
- SpecIF:LocalTerm: Model Elements (Glossary)
- SpecIF:isHeading: true
- SpecIF:Instantiation: user

## SpecIF:UnreferencedResources (SpecIF:TermResourceClass)
- SpecIF:Revision: 1.2
- SpecIF:Domain: SpecIF:DomainBase
- SpecIF:TermStatus: SpecIF:LifecycleStatusReleased
- SpecIF:LocalTerm: Unreferenced Resources (Recycle Bin)
- SpecIF:isHeading: true
- SpecIF:Instantiation: auto

## W3C:Vocabulary (SpecIF:TermResourceClass)
- SpecIF:Revision: 1.2
- dcterms:description: A vocabulary according to the SpecIF class definitions for the domain 'Ontology'.

  There is no clear division between what is referred to as “vocabularies” and “ontologies”. The trend is to use the word “ontology” for more complex, and possibly quite formal collection of terms, whereas “vocabulary” is used when such strict formalism is not necessarily used or only in a very loose sense. Vocabularies are the basic building blocks for inference techniques on the Semantic Web.
- SpecIF:TermStatus: SpecIF:LifecycleStatusEquivalent
- SpecIF:LocalTerm: Vocabulary
- SpecIF:isHeading: true
- SpecIF:Instantiation: user

## W3C:Ontology (SpecIF:TermResourceClass)
- SpecIF:Revision: 1.2
- SpecIF:LocalTerm: Ontology
- dcterms:description: An ontology according to the SpecIF class definitions for the domain 'Ontology'.

  There is no clear division between what is referred to as “vocabularies” and “ontologies”. The trend is to use the word “ontology” for more complex, and possibly quite formal collection of terms, whereas “vocabulary” is used when such strict formalism is not necessarily used or only in a very loose sense. Vocabularies are the basic building blocks for inference techniques on the Semantic Web.
- SpecIF:Domain: SpecIF:DomainOntology
- SpecIF:TermStatus: SpecIF:LifecycleStatusReleased
- SpecIF:isHeading: true
- SpecIF:Instantiation: user

## bpmn:Process (SpecIF:TermResourceClass)
- SpecIF:Revision: 1.2
- SpecIF:Domain: SpecIF:DomainSystemModelIntegration
- SpecIF:TermStatus: SpecIF:LifecycleStatusReleased
- SpecIF:LocalTerm: Business Process
- SpecIF:LocalTermPlural: Business Processes
- SpecIF:isHeading: false
- SpecIF:Instantiation: auto

## bpmn:Participant (SpecIF:TermResourceClass)
- SpecIF:Revision: 1.2
- SpecIF:Domain: SpecIF:DomainSystemModelIntegration
- SpecIF:TermStatus: SpecIF:LifecycleStatusReleased
- SpecIF:LocalTerm: Participant
- SpecIF:LocalTermPlural: Participants
- SpecIF:isHeading: false
- SpecIF:Instantiation: auto

## bpmn:Pool (SpecIF:TermResourceClass)
- SpecIF:Revision: 1.2
- SpecIF:Domain: SpecIF:DomainSystemModelIntegration
- SpecIF:TermStatus: SpecIF:LifecycleStatusEquivalent
- SpecIF:LocalTerm: Pool
- SpecIF:LocalTermPlural: Pools
- SpecIF:isHeading: false
- SpecIF:Instantiation: auto

## bpmn:Lane (SpecIF:TermResourceClass)
- SpecIF:Revision: 1.2
- SpecIF:Domain: SpecIF:DomainSystemModelIntegration
- SpecIF:TermStatus: SpecIF:LifecycleStatusEquivalent
- SpecIF:LocalTerm: Lane
- SpecIF:LocalTermPlural: Lanes
- SpecIF:isHeading: false
- SpecIF:Instantiation: auto

## uml:Package (SpecIF:TermResourceClass)
- SpecIF:Revision: 1.2
- SpecIF:Domain: SpecIF:DomainSystemsEngineering, SpecIF:DomainSystemModelIntegration
- SpecIF:TermStatus: SpecIF:LifecycleStatusReleased
- SpecIF:LocalTerm: Package
- SpecIF:LocalTermPlural: Packages
- SpecIF:isHeading: true
- SpecIF:Instantiation: auto, user

## uml:Actor (SpecIF:TermResourceClass)
- SpecIF:Revision: 1.2
- SpecIF:Domain: SpecIF:DomainSystemModelIntegration
- SpecIF:TermStatus: SpecIF:LifecycleStatusReleased
- SpecIF:LocalTerm: Actor
- SpecIF:LocalTermPlural: Actors
- SpecIF:isHeading: false
- SpecIF:Instantiation: auto

## uml:Port (SpecIF:TermResourceClass)
- SpecIF:Revision: 1.2
- SpecIF:Domain: SpecIF:DomainSystemsEngineering, SpecIF:DomainSystemModelIntegration
- SpecIF:TermStatus: SpecIF:LifecycleStatusReleased
- SpecIF:LocalTerm: Port
- SpecIF:LocalTermPlural: Ports
- SpecIF:isHeading: false
- SpecIF:Instantiation: auto

## uml:StateMachine (SpecIF:TermResourceClass)
- SpecIF:Revision: 1.2
- SpecIF:Domain: SpecIF:DomainSystemsEngineering, SpecIF:DomainSystemModelIntegration
- SpecIF:TermStatus: SpecIF:LifecycleStatusReleased
- SpecIF:LocalTerm: UML State Machine
- SpecIF:LocalTermPlural: UML State Machines
- SpecIF:isHeading: false
- SpecIF:Instantiation: auto

## uml:Activity (SpecIF:TermResourceClass)
- SpecIF:Revision: 1.2
- SpecIF:Domain: SpecIF:DomainSystemsEngineering, SpecIF:DomainSystemModelIntegration
- SpecIF:TermStatus: SpecIF:LifecycleStatusReleased
- SpecIF:LocalTerm: UML Activity
- SpecIF:LocalTermPlural: UML Activities
- SpecIF:isHeading: false
- SpecIF:Instantiation: auto

## uml:Region (SpecIF:TermResourceClass)
- SpecIF:Revision: 1.2
- SpecIF:Domain: SpecIF:DomainSystemsEngineering, SpecIF:DomainSystemModelIntegration
- SpecIF:TermStatus: SpecIF:LifecycleStatusReleased
- SpecIF:LocalTerm: UML Region
- SpecIF:LocalTermPlural: UML Regions
- SpecIF:isHeading: false
- SpecIF:Instantiation: auto

## uml:State (SpecIF:TermResourceClass)
- SpecIF:Revision: 1.2
- SpecIF:Domain: SpecIF:DomainSystemsEngineering, SpecIF:DomainSystemModelIntegration
- SpecIF:TermStatus: SpecIF:LifecycleStatusReleased
- SpecIF:LocalTerm: UML State
- SpecIF:LocalTermPlural: UML States
- SpecIF:isHeading: false
- SpecIF:Instantiation: auto

## uml:Transition (SpecIF:TermResourceClass)
- SpecIF:Revision: 1.2
- SpecIF:Domain: SpecIF:DomainSystemsEngineering, SpecIF:DomainSystemModelIntegration
- SpecIF:TermStatus: SpecIF:LifecycleStatusReleased
- SpecIF:LocalTerm: UML Transition
- SpecIF:LocalTermPlural: UML Transitions
- SpecIF:isHeading: false
- SpecIF:Instantiation: auto

## uml:SignalEvent (SpecIF:TermResourceClass)
- SpecIF:Revision: 1.2
- SpecIF:Domain: SpecIF:DomainSystemsEngineering, SpecIF:DomainSystemModelIntegration
- SpecIF:TermStatus: SpecIF:LifecycleStatusReleased
- SpecIF:LocalTerm: Signal-Event
- SpecIF:LocalTermPlural: Signal-Events
- SpecIF:isHeading: false
- SpecIF:Instantiation: auto

## uml:CallEvent (SpecIF:TermResourceClass)
- SpecIF:Revision: 1.2
- SpecIF:Domain: SpecIF:DomainSystemsEngineering, SpecIF:DomainSystemModelIntegration
- SpecIF:TermStatus: SpecIF:LifecycleStatusReleased
- SpecIF:LocalTerm: Call-Event
- SpecIF:LocalTermPlural: Call-Events
- SpecIF:isHeading: false
- SpecIF:Instantiation: auto

## uml:ChangeEvent (SpecIF:TermResourceClass)
- SpecIF:Revision: 1.2
- SpecIF:Domain: SpecIF:DomainSystemsEngineering, SpecIF:DomainSystemModelIntegration
- SpecIF:TermStatus: SpecIF:LifecycleStatusReleased
- SpecIF:LocalTerm: Change-Event
- SpecIF:LocalTermPlural: Change-Events
- SpecIF:isHeading: false
- SpecIF:Instantiation: auto

## uml:CallBehaviorAction (SpecIF:TermResourceClass)
- SpecIF:Revision: 1.2
- SpecIF:Domain: SpecIF:DomainSystemsEngineering, SpecIF:DomainSystemModelIntegration
- SpecIF:TermStatus: SpecIF:LifecycleStatusReleased
- SpecIF:LocalTerm: UML Call Behavior Action
- SpecIF:LocalTermPlural: UML Call Behavior Actions
- SpecIF:isHeading: false
- SpecIF:Instantiation: auto

## uml:InitialNode (SpecIF:TermResourceClass)
- SpecIF:Revision: 1.2
- SpecIF:LocalTerm: UML Activity Initial Node
- SpecIF:LocalTermPlural: UML Activity Initial Nodes
- SpecIF:isHeading: false
- SpecIF:Instantiation: auto

## uml:ActivityFinalNode (SpecIF:TermResourceClass)
- SpecIF:Revision: 1.2
- SpecIF:Domain: SpecIF:DomainSystemsEngineering, SpecIF:DomainSystemModelIntegration
- SpecIF:TermStatus: SpecIF:LifecycleStatusReleased
- SpecIF:LocalTerm: UML Activity Final Node
- SpecIF:LocalTermPlural: UML Activity Final Nodes
- SpecIF:isHeading: false
- SpecIF:Instantiation: auto

## sysml:Requirement (SpecIF:TermResourceClass)
- SpecIF:Revision: 1.2
- SpecIF:Domain: SpecIF:DomainSystemsEngineering, SpecIF:DomainSystemModelIntegration
- SpecIF:TermStatus: SpecIF:LifecycleStatusEquivalent
- SpecIF:LocalTerm: Requirement
- SpecIF:LocalTermPlural: Requirements
- SpecIF:isHeading: false
- SpecIF:Instantiation: auto, user

## bpmn:processStep (SpecIF:TermResourceClass)
- dcterms:description: A defined value for the [[dcterms:type]] property of [[FMC:Actor]] when used to represent a process step.
- SpecIF:Domain: SpecIF:DomainSystemsEngineering, SpecIF:DomainSystemModelIntegration
- SpecIF:TermStatus: SpecIF:LifecycleStatusExperimental
- SpecIF:LocalTerm: Process Step
- SpecIF:LocalTermPlural: Process Steps
- SpecIF:isHeading: false

## bpmn:dataObject (SpecIF:TermResourceClass)
- SpecIF:Revision: 1.2
- dcterms:description: A defined value for the [[dcterms:type]] property of [[FMC:Actor]] when used to represent a process step.
- SpecIF:Domain: SpecIF:DomainSystemsEngineering, SpecIF:DomainSystemModelIntegration
- SpecIF:TermStatus: SpecIF:LifecycleStatusExperimental
- SpecIF:LocalTerm: Data Object
- SpecIF:LocalTermPlural: Data Objects
- SpecIF:isHeading: false

## bpmn:dataStore (SpecIF:TermResourceClass)
- SpecIF:Revision: 1.2
- dcterms:description: A defined value for the [[dcterms:type]] property of [[FMC:Actor]] when used to represent a process step.
- SpecIF:Domain: SpecIF:DomainSystemsEngineering, SpecIF:DomainSystemModelIntegration
- SpecIF:TermStatus: SpecIF:LifecycleStatusExperimental
- SpecIF:LocalTerm: Data Store
- SpecIF:LocalTermPlural: Data Stores
- SpecIF:isHeading: false

## bpmn:startEvent (SpecIF:TermResourceClass)
- dcterms:description: A defined value for the [[dcterms:type]] property of [[FMC:Event]] when used to represent a general start event.
- SpecIF:TermStatus: SpecIF:LifecycleStatusExperimental
- SpecIF:LocalTerm: Start Event

## bpmn:intermediateEvent (SpecIF:TermResourceClass)
- dcterms:description: A defined value for the [[dcterms:type]] property of [[FMC:Event]] when used to represent a general intermediate event.
- SpecIF:TermStatus: SpecIF:LifecycleStatusExperimental
- SpecIF:LocalTerm: Intermediate Event

## bpmn:endEvent (SpecIF:TermResourceClass)
- dcterms:description: A defined value for the [[dcterms:type]] property of [[FMC:Event]] when used to represent a general end event.
- SpecIF:TermStatus: SpecIF:LifecycleStatusExperimental
- SpecIF:LocalTerm: End Event

## bpmn:join (SpecIF:TermResourceClass)
- dcterms:description: A defined value for the [[dcterms:type]] property of [[FMC:Actor]] when used to represent a 'Join' element in models created with BPMN.
- SpecIF:TermStatus: SpecIF:LifecycleStatusExperimental
- SpecIF:LocalTerm: Join

## bpmn:timer (SpecIF:TermResourceClass)
- dcterms:description: A defined value for the [[dcterms:type]] property of [[FMC:Actor]] when used to represent a 'Timer' element in models created with BPMN.
- SpecIF:TermStatus: SpecIF:LifecycleStatusExperimental
- SpecIF:LocalTerm: Timer

## IREB:Stakeholder (SpecIF:TermResourceClass)
- dcterms:description: A person or organization that has a (direct or indirect) influence on a system’s requirements. Indirect influence also includes situations where a person or organization is impacted by the system.
  This is a subclass of [[FMC:Actor]], more precisely a value of it's property [[dcterms:type]].
- SpecIF:TermStatus: SpecIF:LifecycleStatusReleased
- SpecIF:LocalTerm: Stakeholder
- SpecIF:Instantiation: auto, user

## ReqIF-WF.Customer (SpecIF:TermResourceClass)
- SpecIF:Revision: 1.2
- SpecIF:Domain: SpecIF:DomainRequirementsEngineeringSRC
- SpecIF:TermStatus: SpecIF:LifecycleStatusReleased
- SpecIF:LocalTerm: Customer, Client, Purchaser
- SpecIF:Instantiation: auto

## ReqIF-WF.Supplier (SpecIF:TermResourceClass)
- SpecIF:Revision: 1.2
- SpecIF:Domain: SpecIF:DomainRequirementsEngineeringSRC
- SpecIF:TermStatus: SpecIF:LifecycleStatusReleased
- SpecIF:LocalTerm: Supplier, Vendor, Service Provider, Contractor, Seller
- SpecIF:Instantiation: auto

## SpecIF:Reader (SpecIF:TermResourceClass)
- SpecIF:Revision: 1.2
- SpecIF:Domain: SpecIF:DomainRequirementsEngineering, SpecIF:DomainRequirementsEngineeringSRC, SpecIF:DomainSystemModelIntegration
- SpecIF:TermStatus: SpecIF:LifecycleStatusReleased
- SpecIF:LocalTerm: Reader
- SpecIF:LocalTermPlural: Readers
- SpecIF:Instantiation: auto

## SpecIF:Editor (SpecIF:TermResourceClass)
- SpecIF:Revision: 1.2
- SpecIF:Domain: SpecIF:DomainRequirementsEngineering, SpecIF:DomainRequirementsEngineeringSRC, SpecIF:DomainSystemModelIntegration
- SpecIF:TermStatus: SpecIF:LifecycleStatusReleased
- SpecIF:LocalTerm: Editor
- SpecIF:LocalTermPlural: Editors
- SpecIF:Instantiation: auto

## SpecIF:UserRole (SpecIF:TermResourceClass)
- dcterms:description: This is a subclass of [[FMC:Actor]]; more precisely a value of it's property [[dcterms:type]].
- SpecIF:TermStatus: SpecIF:LifecycleStatusExperimental
- SpecIF:LocalTerm: User Role
- SpecIF:Instantiation: auto, user

## SpecIF:Feature (SpecIF:TermResourceClass)
- SpecIF:Revision: 1.2
- dcterms:description: A 'Feature' is an intentional distinguishing characteristic of a system, often a unique selling proposition.
- SpecIF:Domain: SpecIF:DomainRequirementsEngineering, SpecIF:DomainRequirementsEngineeringSRC, SpecIF:DomainSystemModelIntegration
- SpecIF:TermStatus: SpecIF:LifecycleStatusReleased
- SpecIF:LocalTerm: Feature
- SpecIF:LocalTermPlural: Features
- SpecIF:Icon: ✶
- SpecIF:isHeading: false
- SpecIF:Instantiation: user

## SpecIF:UserStory (SpecIF:TermResourceClass)
- SpecIF:Revision: 1.2
- dcterms:description: A user story is an informal, general explanation of a software feature written from the perspective of the end user. Its purpose is to articulate how a software feature will provide value to the customer.
  This is a subclass of [[IREB:Requirement]], more precisely a value of it's property [[dcterms:type]].
- SpecIF:Domain: SpecIF:DomainRequirementsEngineering, SpecIF:DomainRequirementsEngineeringSRC, SpecIF:DomainSystemModelIntegration, SpecIF:DomainVariantManagement
- SpecIF:TermStatus: SpecIF:LifecycleStatusReleased
- SpecIF:LocalTerm: User Story
- SpecIF:LocalTermPlural: User Stories
- SpecIF:Icon: ☺
- SpecIF:Instantiation: auto, user

## SpecIF:PainPoint (SpecIF:TermResourceClass)
- SpecIF:Revision: 1.2
- dcterms:description: A problem, frustration, or troublesome issue, especially one experienced by consumers, customers, or employees: Getting stuck in a slow checkout line is a major pain point for grocery shoppers.
  This is a subclass of [[IREB:Requirement]], more precisely a value of it's property [[dcterms:type]].
- SpecIF:Domain: SpecIF:DomainRequirementsEngineering
- SpecIF:TermStatus: SpecIF:LifecycleStatusReleased
- SpecIF:LocalTerm: Pain Point
- SpecIF:Icon: ✂
- SpecIF:Instantiation: auto, user

## ArchiMate:ApplicationComponent (SpecIF:TermResourceClass)
- SpecIF:Revision: 1.2
- dcterms:description: Definition: An application component represents an encapsulation of application functionality aligned to implementation structure, which is modular and replaceable. It encapsulates its behavior and data, exposes services, and makes them available through interfaces.
  An application component is a self-contained unit. As such, it is independently deployable, re-usable, and replaceable. An application component performs one or more application functions. It encapsulates its contents: its functionality is only accessible through a set of application interfaces. Cooperating application components are connected via application collaborations.
  An application component may be assigned to one or more application functions. An application component has one or more application interfaces, which expose its functionality. Application interfaces of other application components may serve an application component. The name of an application component should preferably be a noun.
  The application component element is used to model entire applications (i.e., deployed and operational IT systems, as defined by the TOGAF framework) and individual parts of such applications, at all relevant levels of detail.
  Source: ArchiMate® 3.0 Specification
- SpecIF:Domain: SpecIF:DomainSystemsEngineering, SpecIF:DomainSystemModelIntegration
- SpecIF:TermStatus: SpecIF:LifecycleStatusReleased
- SpecIF:LocalTerm: Application Component
- SpecIF:LocalTermPlural: Application Components
- SpecIF:isHeading: false
- SpecIF:Instantiation: auto

## ArchiMate:DataObject (SpecIF:TermResourceClass)
- SpecIF:Revision: 1.2
- dcterms:description: Definition: A data object represents data structured for automated processing.
  A data object should be a self-contained piece of information with a clear meaning to the business, not just to the application level. Typical examples of data objects are a customer record, a client database, or an insurance claim.
  The ArchiMate language in general focuses on the modeling of types, not instances, since this is the most relevant at the Enterprise Architecture level of description. Hence a data object typically models an object type (cf. a UML class) of which multiple instances may exist in operational applications. An important exception is when a data object is used to model a data collection such as a database, of which only one instance exists.
  An application function or process can operate on data objects. A data object may be communicated via interactions and used or produced by application services. A data object can be accessed by an application function, application interaction, or application service. A data object may realize a business object, and may be realized by an artifact. A data object may have association, specialization, aggregation, or composition relationships with other data objects. The name of a data object should preferably be a noun.
  Source: ArchiMate® 3.0 Specification
- SpecIF:Domain: SpecIF:DomainSystemsEngineering, SpecIF:DomainSystemModelIntegration
- SpecIF:TermStatus: SpecIF:LifecycleStatusReleased
- SpecIF:LocalTerm: Data Object
- SpecIF:LocalTermPlural: Data Objects
- SpecIF:isHeading: false
- SpecIF:Instantiation: auto

## ArchiMate:BusinessObject (SpecIF:TermResourceClass)
- SpecIF:Revision: 1.2
- dcterms:description: Definition: A business object represents a concept used within a particular business domain.
  The ArchiMate language in general focuses on the modeling of types, not instances, since this is the most relevant at the Enterprise Architecture level of description. Hence a business object typically models an object type (cf. a UML class) of which multiple instances may exist in operations. Only occasionally, business objects represent actual instances of information produced and consumed by behavior elements such as business processes. This is in particular the case for singleton types; i.e., types that have only one instance.
  A wide variety of types of business objects can be defined. Business objects are passive in the sense that they do not trigger or perform processes. A business object could be used to represent information assets that are relevant from a business point of view and can be realized by data objects.
  Business objects may be accessed (e.g., in the case of information objects, they may be created, read, written) by a business process, function, business interaction, business event, or business service. A business object may have association, specialization, aggregation, or composition relationships with other business objects. A business object may be realized by a representation or by a data object (or both). The name of a business object should preferably be a noun.
  Source: ArchiMate® 3.0 Specification
- SpecIF:Domain: SpecIF:DomainSystemsEngineering, SpecIF:DomainSystemModelIntegration
- SpecIF:TermStatus: SpecIF:LifecycleStatusReleased
- SpecIF:LocalTerm: Business Object
- SpecIF:LocalTermPlural: Business Objects
- SpecIF:isHeading: false
- SpecIF:Instantiation: auto

## DDP:Source (SpecIF:TermResourceClass)
- SpecIF:Revision: 1.2
- dcterms:description: A 'Source' is a file containing partial model information created by an authoring system.
- SpecIF:Domain: SpecIF:DomainSystemModelIntegration
- SpecIF:TermStatus: SpecIF:LifecycleStatusSubmitted
- SpecIF:LocalTerm: Source File
- SpecIF:LocalTermPlural: Source Files
- SpecIF:Icon: 🗎
- SpecIF:isHeading: false
- SpecIF:Instantiation: auto, user

## Statement Class Terms (SpecIF:Heading)
- dcterms:description: A statement represents a logic affinity or association between two resources, i.e. system specification artefacts. The terms listed in this chapter may be used as predicates to distinguish different classes (types) of statements. Each statement class may define an individual set of properties for carrying the information 'payload'.
  In SpecIF, a statement is first order predicate logic. For each predicate (statement class), a list of eligible resource classes may be defined for subjects and objects, respectively. For example, the predicate [[oslc_rm:satisfies]] is usually confined to [[FMC:Actor]] and [[FMC:State]] as subject and [[IREB:Requirement]] as object.
  A statement consisting of subject-predicate-object (where a resource may serve as subject or object) can be directly mapped to a ReqIF relation, a RDF triple in OSLC or 'linked data' in general.
  A statement class corresponds to a 'SPEC-RELATION-TYPE' and a statement is a 'SPEC-RELATION' in the Requirements Interchange Format (ReqIF). In ArchiMate® 3.0, a statement is a Relationship.

## SpecIF:relates (SpecIF:TermStatementClass)
- SpecIF:Revision: 1.2
- dcterms:description: Is a generalized type for model relations.
- SpecIF:Domain: SpecIF:DomainOntology
- SpecIF:TermStatus: SpecIF:LifecycleStatusSubmitted
- SpecIF:LocalTerm: associated with
- SpecIF:isUndirected: false
- SpecIF:Instantiation: auto

## SpecIF:shows (SpecIF:TermStatementClass)
- dcterms:identifier: SC-shows
- SpecIF:Revision: 1.1
- dcterms:description: A [[SpecIF:Diagram]] 'shows' a model element, e.g, a [[FMC:Actor]], [[FMC:State]], [[FMC:Event]] or [[SpecIF:Collection]].
- SpecIF:Domain: SpecIF:DomainSystemModelIntegration
- SpecIF:TermStatus: SpecIF:LifecycleStatusReleased
- SpecIF:LocalTerm: shows
- SpecIF:isUndirected: false
- SpecIF:Instantiation: auto

## SpecIF:contains (SpecIF:TermStatementClass)
- dcterms:identifier: SC-contains
- SpecIF:Revision: 1.1
- dcterms:description: General containment, such as:
  - Package-A *contains* Diagram-B
  - Collection-1 *contains* DataObject-1.1

  Not to confound with *[[dcterms:hasPart]]*.
- SpecIF:Domain: SpecIF:DomainSystemModelIntegration
- SpecIF:TermStatus: SpecIF:LifecycleStatusReleased
- SpecIF:LocalTerm: contains
- SpecIF:isUndirected: false
- SpecIF:Instantiation: auto

## dcterms:hasPart (SpecIF:TermStatementClass)
- SpecIF:Revision: 1.2
- dcterms:description: A related resource that is included either physically or logically in the described resource.

  *Comment: This property is intended to be used with non-literal values. This property is an inverse property of [[dcterms:isPartOf]].*
- SpecIF:Domain: SpecIF:DomainSystemModelIntegration
- SpecIF:TermStatus: SpecIF:LifecycleStatusReleased
- SpecIF:LocalTerm: has part
- SpecIF:isUndirected: false
- SpecIF:Instantiation: auto

## dcterms:isPartOf (SpecIF:TermStatementClass)
- SpecIF:Revision: 1.2
- dcterms:description: A related resource in which the described resource is physically or logically included.

  *Comment: This property is intended to be used with non-literal values. This property is an inverse property of [[dcterms:hasPart]].*
- SpecIF:Domain: SpecIF:DomainSystemModelIntegration
- SpecIF:TermStatus: SpecIF:LifecycleStatusEquivalent
- SpecIF:LocalTerm: is part of
- SpecIF:isUndirected: false
- SpecIF:Instantiation: auto

## SpecIF:hasItem (SpecIF:TermStatementClass)
- SpecIF:Revision: 1.2
- dcterms:description: Containment relationship reserved for use in a hierarchy.
- SpecIF:Domain: SpecIF:DomainRequirementsEngineering, SpecIF:DomainRequirementsEngineeringSRC, SpecIF:DomainSystemsEngineering, SpecIF:DomainSystemModelIntegration
- SpecIF:TermStatus: SpecIF:LifecycleStatusSubmitted
- SpecIF:LocalTerm: has item
- SpecIF:isUndirected: false
- SpecIF:Instantiation: auto, user

## ArchiMate:Uniting (SpecIF:TermStatementClass)
- SpecIF:Revision: 1.2
- dcterms:description: General containment. In ArchiMate, the uniting concept includes:
  - The *composition* relationship represents that an element consists of one or more other concepts.
  - The *aggregation* relationship represents that an element combines one or more other concepts.
  - The *assignment* relationship represents the allocation of responsibility, performance of behavior, storage, or execution.
  - The *realization* relationship represents that an entity plays a critical role in the creation, achievement, sustenance, or operation of a more abstract entity.

  The kind of uniting is specified in a property with title [[dcterms:type]].
- SpecIF:Domain: SpecIF:DomainSystemModelIntegration
- SpecIF:TermStatus: SpecIF:LifecycleStatusEquivalent
- SpecIF:LocalTerm: unites
- SpecIF:isUndirected: false
- SpecIF:Instantiation: auto

## FMC:contains (SpecIF:TermStatementClass)
- SpecIF:Revision: 1.2
- dcterms:description: A [[FMC:Actor]] or [[FMC:State]] 'contains' a [[FMC:Actor]], [[FMC:State]] or [[FMC:Event]]. More concretely, Component-A contains Component-B.
- SpecIF:Domain: SpecIF:DomainSystemsEngineering, SpecIF:DomainSystemModelIntegration
- SpecIF:TermStatus: SpecIF:LifecycleStatusReleased
- SpecIF:LocalTerm: contains
- SpecIF:isUndirected: false
- SpecIF:Instantiation: auto

## FMC:requests (SpecIF:TermStatementClass)
- SpecIF:Revision: 1.2
- SpecIF:Domain: SpecIF:DomainSystemsEngineering, SpecIF:DomainSystemModelIntegration
- SpecIF:TermStatus: SpecIF:LifecycleStatusSubmitted
- SpecIF:LocalTerm: requests
- SpecIF:isUndirected: false
- SpecIF:Instantiation: auto

## SpecIF:satisfies (SpecIF:TermStatementClass)
- dcterms:description: A [[FMC:Actor]] or [[FMC:State]] 'satisfies' a [[IREB:Requirement]].
- SpecIF:LocalTerm: satisfies
- SpecIF:TermStatus: SpecIF:LifecycleStatusEquivalent

## SpecIF:implies (SpecIF:TermStatementClass)
- SpecIF:Revision: 1.2
- dcterms:description: A law or regulation implies a requirement.
- SpecIF:Domain: SpecIF:DomainSystemsEngineering, SpecIF:DomainSystemModelIntegration
- SpecIF:TermStatus: SpecIF:LifecycleStatusSubmitted
- SpecIF:LocalTerm: implies
- SpecIF:isUndirected: false
- SpecIF:Instantiation: auto, user

## SpecIF:impliedBy (SpecIF:TermStatementClass)
- SpecIF:Revision: 1.2
- dcterms:description: A requirement is implied by a law or rgulation
- SpecIF:Domain: SpecIF:DomainSystemsEngineering, SpecIF:DomainSystemModelIntegration
- SpecIF:TermStatus: SpecIF:LifecycleStatusSubmitted
- SpecIF:LocalTerm: is implied by
- SpecIF:isUndirected: false
- SpecIF:Instantiation: auto, user

## SpecIF:implements (SpecIF:TermStatementClass)
- dcterms:description: A [[FMC:Actor]] or [[FMC:State]] 'implements' a [[SpecIF:Feature]].
- SpecIF:TermStatus: SpecIF:LifecycleStatusEquivalent
- SpecIF:LocalTerm: implements
- SpecIF:isUndirected: false

## SpecIF:influences (SpecIF:TermStatementClass)
- dcterms:description: The influence relationship represents that an element affects the implementation or achievement of some motivation element.
- SpecIF:LocalTerm: influences
- SpecIF:Domain: SpecIF:DomainSystemModelIntegration
- SpecIF:TermStatus: SpecIF:LifecycleStatusExperimental

## SpecIF:isResponsibleFor (SpecIF:TermStatementClass)
- dcterms:identifier: SC-SpecifIsresponsiblefor
- SpecIF:Revision: 1.2
- dcterms:description: The influence relationship represents that an element affects the implementation or achievement of some motivation element.
- SpecIF:Domain: SpecIF:DomainSystemsEngineering, SpecIF:DomainSystemModelIntegration
- SpecIF:TermStatus: SpecIF:LifecycleStatusReleased
- SpecIF:LocalTerm: is responsible for
- SpecIF:isUndirected: false
- SpecIF:Instantiation: auto, user

## SpecIF:isResponsibilityOf (SpecIF:TermStatementClass)
- dcterms:identifier: SC-SpecifIsresponsibilityof
- SpecIF:Revision: 1.2
- SpecIF:Domain: SpecIF:DomainSystemsEngineering, SpecIF:DomainSystemModelIntegration
- SpecIF:TermStatus: SpecIF:LifecycleStatusSubmitted
- SpecIF:LocalTerm: is responsibility of
- SpecIF:isUndirected: false
- SpecIF:Instantiation: auto, user

## rdf:type (SpecIF:TermStatementClass)
- dcterms:description: A triple of the form: R rdf:type C states that C is an instance of rdfs:Class and R is an instance of C.
  The rdfs:domain of rdf:type is rdfs:Resource. The rdfs:range of rdf:type is rdfs:Class.
- SpecIF:Domain: SpecIF:DomainSystemModelIntegration
- SpecIF:TermStatus: SpecIF:LifecycleStatusReleased
- SpecIF:LocalTerm: Type
- SpecIF:Instantiation: auto

## oslc_rm:satisfies (SpecIF:TermStatementClass)
- SpecIF:Revision: 1.2
- dcterms:description: The object is satisfied by the subject. (source: OSLC)
  SpecIF suggests that the subject is confined to a model element, e.g, a [[FMC:Actor]] or [[FMC:State]], and the object is confined to a [[IREB:Requirement]]. More concretely, an example for this type of statement is 'Component-X satisfies 'Requirement-4711'.
- SpecIF:Domain: SpecIF:DomainRequirementsEngineering, SpecIF:DomainRequirementsEngineeringSRC, SpecIF:DomainSystemsEngineering, SpecIF:DomainSystemModelIntegration
- SpecIF:TermStatus: SpecIF:LifecycleStatusReleased
- SpecIF:LocalTerm: satisfies
- SpecIF:isUndirected: false
- SpecIF:Instantiation: user

## sysml:Satisfy (SpecIF:TermStatementClass)
- SpecIF:Revision: 1.2
- dcterms:description: The object is satisfied by the subject. (source: OSLC)
  SpecIF suggests that the subject is confined to a model element, e.g, a [[FMC:Actor]] or [[FMC:State]], and the object is confined to a [[IREB:Requirement]]. More concretely, an example for this type of statement is 'Component-X satisfies 'Requirement-4711'.
- SpecIF:Domain: SpecIF:DomainSystemsEngineering, SpecIF:DomainSystemModelIntegration
- SpecIF:TermStatus: SpecIF:LifecycleStatusEquivalent
- SpecIF:LocalTerm: satisfies
- SpecIF:isUndirected: false
- SpecIF:Instantiation: auto

## oslc_rm:satisfiedBy (SpecIF:TermStatementClass)
- SpecIF:Revision: 1.2
- dcterms:description: The subject is satisfied by the object. For example, a user requirement is satisfied by a system requirement. (source: OSLC)
- SpecIF:LocalTerm: satisfied by
- SpecIF:Domain: SpecIF:DomainRequirementsEngineering, SpecIF:DomainRequirementsEngineeringSRC, SpecIF:DomainSystemsEngineering, SpecIF:DomainSystemModelIntegration
- SpecIF:TermStatus: SpecIF:LifecycleStatusReleased
- SpecIF:isUndirected: false
- SpecIF:Instantiation: user

## oslc_rm:elaborates (SpecIF:TermStatementClass)
- dcterms:description: The object is elaborated by the subject. For example, a use case elaborates a requirement.
- SpecIF:TermStatus: SpecIF:LifecycleStatusEquivalent
- SpecIF:isUndirected: false

## oslc_rm:elaboratedBy (SpecIF:TermStatementClass)
- dcterms:description: The subject is elaborated by the object.

## oslc_rm:specifies (SpecIF:TermStatementClass)
- dcterms:description: The object is specified by the subject. For example, a requirement specifies a model element.

## oslc_rm:specifiedBy (SpecIF:TermStatementClass)
- dcterms:description: The subject is specified by the object.

## oslc_rm:affectedBy (SpecIF:TermStatementClass)
- dcterms:description: Requirement is affected by a resource, such as a defect or issue.

## oslc_rm:trackedBy (SpecIF:TermStatementClass)
- dcterms:description: Resource, such as a change request, which tracks this requirement.

## oslc_rm:implementedBy (SpecIF:TermStatementClass)
- dcterms:description: Resource, such as a change request, which implements this requirement.
- SpecIF:Domain: SpecIF:DomainSystemModelIntegration
- SpecIF:TermStatus: SpecIF:LifecycleStatusReleased
- SpecIF:LocalTerm: implemented by
- SpecIF:isUndirected: false

## oslc_rm:implements (SpecIF:TermStatementClass)
- dcterms:description: Resource, such as a change request, which implements this requirement.
- SpecIF:Domain: SpecIF:DomainSystemModelIntegration
- SpecIF:TermStatus: SpecIF:LifecycleStatusReleased
- SpecIF:LocalTerm: implements
- SpecIF:isUndirected: false

## oslc_rm:validatedBy (SpecIF:TermStatementClass)
- dcterms:description: Resource, such as a test case, which validates this requirement.
- SpecIF:Domain: SpecIF:DomainSystemTesting
- SpecIF:TermStatus: SpecIF:LifecycleStatusSubmitted
- SpecIF:LocalTerm: validated by
- SpecIF:isUndirected: false

## oslc_rm:validates (SpecIF:TermStatementClass)
- dcterms:description: Resource, such as a test case, which validates this requirement.
- SpecIF:Domain: SpecIF:DomainSystemTesting
- SpecIF:LocalTerm: validates
- SpecIF:isUndirected: false

## oslc_rm:decomposes (SpecIF:TermStatementClass)
- dcterms:description: The object is decomposed by the subject. For example, a collection of subsystems decomposes a system.
- SpecIF:Domain: SpecIF:DomainSystemModelIntegration
- SpecIF:TermStatus: SpecIF:LifecycleStatusEquivalent
- SpecIF:LocalTerm: decomposes
- SpecIF:isUndirected: false

## oslc_rm:decomposedBy (SpecIF:TermStatementClass)
- dcterms:description: The subject is decomposed by the object.
- SpecIF:Domain: SpecIF:DomainSystemModelIntegration
- SpecIF:LocalTerm: decomposed by
- SpecIF:isUndirected: false

## oslc_rm:constrains (SpecIF:TermStatementClass)
- dcterms:description: The object is constrained by the subject. For example, a safety requirement constrains a functional requirement.
- SpecIF:Domain: SpecIF:DomainSystemModelIntegration
- SpecIF:LocalTerm: constrains

## oslc_rm:constrainedBy (SpecIF:TermStatementClass)
- dcterms:description: The subject is constrained by the object.
- SpecIF:LocalTerm: constrained by

## SpecIF:serves (SpecIF:TermStatementClass)
- SpecIF:Revision: 1.2
- dcterms:description: A [[FMC:Actor]] 'serves' a FMC:Actor.
- SpecIF:Domain: SpecIF:DomainSystemsEngineering, SpecIF:DomainSystemModelIntegration
- SpecIF:TermStatus: SpecIF:LifecycleStatusReleased
- SpecIF:LocalTerm: serves
- SpecIF:isUndirected: false
- SpecIF:Instantiation: auto

## ArchiMate:Serving (SpecIF:TermStatementClass)
- SpecIF:Revision: 1.2
- dcterms:description: The serving relationship indicates that an element provides its functionality to another element. (Quelle: ArchiMate 3.1. Relationships)
- SpecIF:Domain: SpecIF:DomainSystemsEngineering, SpecIF:DomainSystemModelIntegration
- SpecIF:TermStatus: SpecIF:LifecycleStatusEquivalent
- SpecIF:LocalTerm: serves
- SpecIF:isUndirected: false
- SpecIF:Instantiation: auto

## SpecIF:handles (SpecIF:TermStatementClass)
- SpecIF:Revision: 1.2
- dcterms:description: The relationship indicates that an element (represented by a [[FMC:Actor]]) provides or consumes material, energy or information (represented by a [[FMC:State]]).
- SpecIF:Domain: SpecIF:DomainSystemsEngineering, SpecIF:DomainSystemModelIntegration
- SpecIF:TermStatus: SpecIF:LifecycleStatusSubmitted
- SpecIF:LocalTerm: handles
- SpecIF:isUndirected: false
- SpecIF:Instantiation: auto

## SpecIF:consumes (SpecIF:TermStatementClass)
- SpecIF:Revision: 1.2
- SpecIF:Domain: SpecIF:DomainSystemsEngineering, SpecIF:DomainSystemModelIntegration
- SpecIF:TermStatus: SpecIF:LifecycleStatusReleased
- SpecIF:LocalTerm: consumes
- SpecIF:isUndirected: false
- SpecIF:Instantiation: auto

## SpecIF:provides (SpecIF:TermStatementClass)
- SpecIF:Revision: 1.2
- SpecIF:Domain: SpecIF:DomainSystemsEngineering, SpecIF:DomainSystemModelIntegration
- SpecIF:TermStatus: SpecIF:LifecycleStatusReleased
- SpecIF:LocalTerm: provides
- SpecIF:isUndirected: false
- SpecIF:Instantiation: auto

## SpecIF:accesses (SpecIF:TermStatementClass)
- SpecIF:Revision: 1.2
- dcterms:description: A [[FMC:Actor]] 'accesses' (writes and reads) a [[FMC:State]].
- SpecIF:Domain: SpecIF:DomainSystemsEngineering, SpecIF:DomainSystemModelIntegration
- SpecIF:TermStatus: SpecIF:LifecycleStatusReleased
- SpecIF:LocalTerm: accesses, stores, stores
- SpecIF:isUndirected: false
- SpecIF:Instantiation: auto

## SpecIF:reads (SpecIF:TermStatementClass)
- SpecIF:Revision: 1.2
- dcterms:description: A [[FMC:Actor]] 'reads' a [[FMC:State]].
- SpecIF:LocalTerm: reads
- SpecIF:Domain: SpecIF:DomainSystemModelIntegration
- SpecIF:TermStatus: SpecIF:LifecycleStatusReleased
- SpecIF:isUndirected: false
- SpecIF:Instantiation: auto

## SpecIF:writes (SpecIF:TermStatementClass)
- SpecIF:Revision: 1.2
- dcterms:description: A [[FMC:Actor]] 'writes' (changes) a [[FMC:State]].
- SpecIF:LocalTerm: writes
- SpecIF:Domain: SpecIF:DomainSystemModelIntegration
- SpecIF:TermStatus: SpecIF:LifecycleStatusReleased
- SpecIF:isUndirected: false
- SpecIF:Instantiation: auto

## SpecIF:stores (SpecIF:TermStatementClass)
- SpecIF:Revision: 1.2
- dcterms:description: A [[FMC:Actor]] 'stores' (writes and reads) a [[FMC:State]].
- SpecIF:Domain: SpecIF:DomainSystemModelIntegration
- SpecIF:TermStatus: SpecIF:LifecycleStatusDeprecated
- SpecIF:LocalTerm: stores
- SpecIF:isUndirected: false
- SpecIF:Instantiation: auto

## bpmn:dataInputAssociation (SpecIF:TermStatementClass)
- SpecIF:Revision: 1.2
- SpecIF:Domain: SpecIF:DomainSystemsEngineering, SpecIF:DomainSystemModelIntegration
- SpecIF:TermStatus: SpecIF:LifecycleStatusEquivalent
- SpecIF:LocalTerm: has input
- SpecIF:isUndirected: false
- SpecIF:Instantiation: auto, user

## bpmn:dataOutputAssociation (SpecIF:TermStatementClass)
- SpecIF:Revision: 1.2
- SpecIF:Domain: SpecIF:DomainSystemsEngineering, SpecIF:DomainSystemModelIntegration
- SpecIF:TermStatus: SpecIF:LifecycleStatusEquivalent
- SpecIF:LocalTerm: has output
- SpecIF:isUndirected: false
- SpecIF:Instantiation: auto, user

## ArchiMate:Access (SpecIF:TermStatementClass)
- dcterms:description: A [[FMC:Actor]] 'accesses' (writes and reads) a [[FMC:State]].
- SpecIF:Domain: SpecIF:DomainSystemsEngineering, SpecIF:DomainSystemModelIntegration
- SpecIF:TermStatus: SpecIF:LifecycleStatusEquivalent
- SpecIF:LocalTerm: accesses, stores
- SpecIF:isUndirected: false
- SpecIF:Instantiation: auto

## ArchiMate:Realization (SpecIF:TermStatementClass)
- dcterms:description: A business function realizes a business capability or an application component realizes a business function.
- SpecIF:Domain: SpecIF:DomainSystemModelIntegration
- SpecIF:TermStatus: SpecIF:LifecycleStatusReleased
- SpecIF:LocalTerm: realizes
- SpecIF:isUndirected: false
- SpecIF:Instantiation: auto

## SpecIF:realizes (SpecIF:TermStatementClass)
- dcterms:description: A business function realizes a business capability or an application component realizes a business function.
- SpecIF:Domain: SpecIF:DomainSystemModelIntegration
- SpecIF:TermStatus: SpecIF:LifecycleStatusEquivalent
- SpecIF:LocalTerm: realizes
- SpecIF:isUndirected: false
- SpecIF:Instantiation: auto

## ArchiMate:Assignment (SpecIF:TermStatementClass)
- dcterms:description: The assignment relationship represents the allocation of responsibility, performance of behavior, storage, or execution.
- SpecIF:Domain: SpecIF:DomainSystemsEngineering, SpecIF:DomainSystemModelIntegration
- SpecIF:TermStatus: SpecIF:LifecycleStatusReleased
- SpecIF:LocalTerm: is assigned to
- SpecIF:isUndirected: false
- SpecIF:Instantiation: auto

## SpecIF:realizedBy (SpecIF:TermStatementClass)
- dcterms:description: A business capability is realized by a business function or a business function is realized by an application component.
- SpecIF:Domain: SpecIF:DomainSystemModelIntegration
- SpecIF:TermStatus: SpecIF:LifecycleStatusReleased
- SpecIF:LocalTerm: wird realisiert von
- SpecIF:isUndirected: false
- SpecIF:Instantiation: auto

## FMC:modifies (SpecIF:TermStatementClass)
- dcterms:description: A [[FMC:Actor]] writes *and* reads a [[FMC:State]].
- SpecIF:LocalTerm: modifies
- SpecIF:Domain: SpecIF:DomainSystemModelIntegration
- SpecIF:TermStatus: SpecIF:LifecycleStatusEquivalent

## FMC:communicatesWith (SpecIF:TermStatementClass)
- SpecIF:Revision: 1.2
- dcterms:description: A [[FMC:Actor]] 'communicates' with a [[FMC:Actor]].
- SpecIF:LocalTerm: communicates with
- SpecIF:Domain: SpecIF:DomainSystemModelIntegration
- SpecIF:TermStatus: SpecIF:LifecycleStatusReleased
- SpecIF:isUndirected: false
- SpecIF:Instantiation: auto

## FMC:sendsTo (SpecIF:TermStatementClass)
- SpecIF:Revision: 1.2
- dcterms:description: A [[FMC:Actor]] 'sends' a message to a [[FMC:Actor]].
- SpecIF:LocalTerm: sends to
- SpecIF:Domain: SpecIF:DomainSystemModelIntegration
- SpecIF:TermStatus: SpecIF:LifecycleStatusReleased
- SpecIF:isUndirected: false
- SpecIF:Instantiation: auto

## FMC:receivesFrom (SpecIF:TermStatementClass)
- SpecIF:Revision: 1.2
- dcterms:description: A [[FMC:Actor]] 'receives' a message from a [[FMC:Actor]].
- SpecIF:LocalTerm: receives from
- SpecIF:Domain: SpecIF:DomainSystemModelIntegration
- SpecIF:TermStatus: SpecIF:LifecycleStatusReleased
- SpecIF:isUndirected: false
- SpecIF:Instantiation: auto

## SpecIF:follows (SpecIF:TermStatementClass)
- SpecIF:Revision: 1.2
- dcterms:description: A [[FMC:Actor]] 'follows' a [[FMC:Actor]]; e.g. in a business process or activity flow.
- SpecIF:Domain: SpecIF:DomainSystemModelIntegration
- SpecIF:TermStatus: SpecIF:LifecycleStatusReleased
- SpecIF:LocalTerm: follows
- SpecIF:isUndirected: false
- SpecIF:Instantiation: auto

## SpecIF:precedes (SpecIF:TermStatementClass)
- SpecIF:Revision: 1.2
- dcterms:description: A [[FMC:Actor]] 'precedes' a [[FMC:Actor]]; e.g. in a business process or activity flow.
- SpecIF:Domain: SpecIF:DomainSystemModelIntegration
- SpecIF:TermStatus: SpecIF:LifecycleStatusReleased
- SpecIF:LocalTerm: precedes
- SpecIF:isUndirected: false
- SpecIF:Instantiation: auto

## SpecIF:signals (SpecIF:TermStatementClass)
- dcterms:description: A [[FMC:Actor]] 'signals' a [[FMC:Event]].
- SpecIF:Domain: SpecIF:DomainSystemModelIntegration
- SpecIF:TermStatus: SpecIF:LifecycleStatusDeprecated
- SpecIF:LocalTerm: signals
- SpecIF:isUndirected: false

## SpecIF:triggers (SpecIF:TermStatementClass)
- dcterms:description: A [[FMC:Event]] 'triggers' a [[FMC:Actor]].
- SpecIF:Domain: SpecIF:DomainSystemModelIntegration
- SpecIF:TermStatus: SpecIF:LifecycleStatusDeprecated
- SpecIF:LocalTerm: triggers
- SpecIF:isUndirected: false

## SpecIF:dependsOn (SpecIF:TermStatementClass)
- SpecIF:Revision: 1.2
- dcterms:description: A [[IREB:Requirement]] 'depends on' another [[IREB:Requirement]].
- SpecIF:Domain: SpecIF:DomainRequirementsEngineering, SpecIF:DomainRequirementsEngineeringSRC, SpecIF:DomainSystemModelIntegration
- SpecIF:TermStatus: SpecIF:LifecycleStatusReleased
- SpecIF:LocalTerm: depends on
- SpecIF:isUndirected: false
- SpecIF:Instantiation: user

## sysml:Usage (SpecIF:TermStatementClass)
- SpecIF:Revision: 1.2
- SpecIF:Domain: SpecIF:DomainSystemModelIntegration
- SpecIF:TermStatus: SpecIF:LifecycleStatusReleased
- SpecIF:LocalTerm: uses
- SpecIF:isUndirected: false
- SpecIF:Instantiation: auto

## sysml:Trace (SpecIF:TermStatementClass)
- SpecIF:Revision: 1.2
- dcterms:description: A [[IREB:Requirement]] traces another [[IREB:Requirement]]. This is the most general (yet unspecified) relation between resources.
- SpecIF:Domain: SpecIF:DomainSystemsEngineering, SpecIF:DomainSystemModelIntegration
- SpecIF:TermStatus: SpecIF:LifecycleStatusSubmitted
- SpecIF:isUndirected: false
- SpecIF:Instantiation: user

## sysml:Derive (SpecIF:TermStatementClass)
- SpecIF:Revision: 1.2
- dcterms:description: A [[IREB:Requirement]] 'is derived from' another [[IREB:Requirement]].
- SpecIF:Domain: SpecIF:DomainSystemsEngineering, SpecIF:DomainSystemModelIntegration
- SpecIF:TermStatus: SpecIF:LifecycleStatusReleased
- SpecIF:LocalTerm: derived from
- SpecIF:isUndirected: false
- SpecIF:Instantiation: user

## sysml:Refine (SpecIF:TermStatementClass)
- SpecIF:Revision: 1.2
- dcterms:description: A [[IREB:Requirement]] 'refines' another [[IREB:Requirement]].
- SpecIF:Domain: SpecIF:DomainSystemsEngineering, SpecIF:DomainSystemModelIntegration
- SpecIF:TermStatus: SpecIF:LifecycleStatusEquivalent
- SpecIF:LocalTerm: refines
- SpecIF:isUndirected: false
- SpecIF:Instantiation: auto

## sysml:Allocate (SpecIF:TermStatementClass)
- SpecIF:Revision: 1.2
- dcterms:description: An [[FMC:Actor]] is allocated to another [[FMC:Actor]] (e.g. a logical function is allocated to a physical component.
- SpecIF:Domain: SpecIF:DomainSystemsEngineering, SpecIF:DomainSystemModelIntegration
- SpecIF:TermStatus: SpecIF:LifecycleStatusReleased
- SpecIF:LocalTerm: is allocated to
- SpecIF:isUndirected: false
- SpecIF:Instantiation: auto

## IREB:refines (SpecIF:TermStatementClass)
- SpecIF:Revision: 1.2
- dcterms:description: A [[IREB:Requirement]] 'refines' another [[IREB:Requirement]].
- SpecIF:Domain: SpecIF:DomainRequirementsEngineering
- SpecIF:TermStatus: SpecIF:LifecycleStatusReleased
- SpecIF:LocalTerm: refines
- SpecIF:isUndirected: false
- SpecIF:Instantiation: user

## IREB:refinedBy (SpecIF:TermStatementClass)
- SpecIF:Revision: 1.2
- dcterms:description: A [[IREB:Requirement]] 'is refined by' another [[IREB:Requirement]].
- SpecIF:TermStatus: SpecIF:LifecycleStatusReleased
- SpecIF:LocalTerm: refined by
- SpecIF:isUndirected: false
- SpecIF:Instantiation: user

## SpecIF:duplicates (SpecIF:TermStatementClass)
- SpecIF:Revision: 1.2
- dcterms:description: A [[IREB:Requirement]] 'duplicates' another [[IREB:Requirement]].
- SpecIF:Domain: SpecIF:DomainRequirementsEngineering
- SpecIF:TermStatus: SpecIF:LifecycleStatusReleased
- SpecIF:LocalTerm: duplicates
- SpecIF:isUndirected: true
- SpecIF:Instantiation: user

## dcterms:replaces (SpecIF:TermStatementClass)
- dcterms:identifier: SC-replacesRequirement
- SpecIF:Revision: 1.2
- dcterms:description: A [[IREB:Requirement]] 'replaces' another [[IREB:Requirement]].
- SpecIF:Domain: SpecIF:DomainRequirementsEngineering
- SpecIF:TermStatus: SpecIF:LifecycleStatusReleased
- SpecIF:LocalTerm: replaces
- SpecIF:isUndirected: false
- SpecIF:Instantiation: user

## SpecIF:contradicts (SpecIF:TermStatementClass)
- SpecIF:Revision: 1.2
- dcterms:description: A [[IREB:Requirement]] 'contradicts' another [[IREB:Requirement]].
- SpecIF:Domain: SpecIF:DomainRequirementsEngineering
- SpecIF:TermStatus: SpecIF:LifecycleStatusReleased
- SpecIF:LocalTerm: contradicts
- SpecIF:isUndirected: true
- SpecIF:Instantiation: user

## SpecIF:isAssociatedWith (SpecIF:TermStatementClass)
- dcterms:description: A [[FMC:State]] is associated with another [[FMC:State]] (e.g. a class is associated with another class, as shown in a UML Class Diagram).
- SpecIF:Domain: SpecIF:DomainSystemsEngineering, SpecIF:DomainSystemModelIntegration
- SpecIF:TermStatus: SpecIF:LifecycleStatusReleased
- SpecIF:LocalTerm: associated with
- SpecIF:isUndirected: false
- SpecIF:Instantiation: auto

## ArchiMate:Composition (SpecIF:TermStatementClass)
- SpecIF:Revision: 1.2
- dcterms:description: An [[FMC:Actor]] composes another [[FMC:Actor]].
  The things that something is composed of are its parts or members. The separate things that compose something are the parts or members that form it. Source: Collins Dictionary
- SpecIF:Domain: SpecIF:DomainSystemModelIntegration
- SpecIF:TermStatus: SpecIF:LifecycleStatusExperimental
- SpecIF:LocalTerm: composes
- SpecIF:isUndirected: false
- SpecIF:Instantiation: auto

## uml:Association (SpecIF:TermStatementClass)
- SpecIF:Revision: 1.2
- dcterms:description: A [[FMC:State]] is associated with another [[FMC:State]] (e.g. a class is associated with another class, as shown in a UML Class Diagram).
- SpecIF:Domain: SpecIF:DomainSystemsEngineering, SpecIF:DomainSystemModelIntegration
- SpecIF:TermStatus: SpecIF:LifecycleStatusEquivalent
- SpecIF:LocalTerm: associated with
- SpecIF:isUndirected: false
- SpecIF:Instantiation: auto

## uml:Composition (SpecIF:TermStatementClass)
- SpecIF:Revision: 1.2
- dcterms:description: An [[FMC:Actor]] is composed of another [[FMC:Actor]].
  The things that something is composed of are its parts or members. The separate things that compose something are the parts or members that form it. Source: Collins Dictionary
- SpecIF:Domain: SpecIF:DomainSystemModelIntegration
- SpecIF:TermStatus: SpecIF:LifecycleStatusEquivalent
- SpecIF:LocalTerm: owns, is composed of, is composed of
- SpecIF:isUndirected: false
- SpecIF:Instantiation: auto

## uml:Aggregation (SpecIF:TermStatementClass)
- SpecIF:Revision: 1.2
- dcterms:description: An [[FMC:Actor]] aggregates another [[FMC:Actor]].
  If amounts or things are aggregated, they are added together and considered as a single amount or thing.Source: Collins Dictionary
- SpecIF:Domain: SpecIF:DomainSystemModelIntegration
- SpecIF:TermStatus: SpecIF:LifecycleStatusEquivalent
- SpecIF:LocalTerm: has a, aggregates, besteht aus
- SpecIF:isUndirected: false
- SpecIF:Instantiation: auto

## ArchiMate:Aggregation (SpecIF:TermStatementClass)
- SpecIF:Revision: 1.2
- dcterms:description: An [[FMC:Actor]] aggregates another [[FMC:Actor]].
  If amounts or things are aggregated, they are added together and considered as a single amount or thing.Source: Collins Dictionary
- SpecIF:Domain: SpecIF:DomainSystemModelIntegration
- SpecIF:TermStatus: SpecIF:LifecycleStatusEquivalent
- SpecIF:LocalTerm: aggregates
- SpecIF:isUndirected: false
- SpecIF:Instantiation: auto

## SpecIF:aggregates (SpecIF:TermStatementClass)
- SpecIF:Revision: 1.2
- dcterms:description: An [[FMC:Actor]] aggregates another [[FMC:Actor]].
  If amounts or things are aggregated, they are added together and considered as a single amount or thing.Source: Collins Dictionary
- SpecIF:Domain: SpecIF:DomainSystemsEngineering, SpecIF:DomainSystemModelIntegration
- SpecIF:TermStatus: SpecIF:LifecycleStatusReleased
- SpecIF:LocalTerm: aggregates
- SpecIF:isUndirected: false
- SpecIF:Instantiation: auto

## uml:extends (SpecIF:TermStatementClass)
- SpecIF:Revision: 1.2
- dcterms:description: An [[FMC:Actor]] «UseCase» extends another [[FMC:Actor]] «UseCase».
- SpecIF:Domain: SpecIF:DomainSystemModelIntegration
- SpecIF:TermStatus: SpecIF:LifecycleStatusReleased
- SpecIF:LocalTerm: extends
- SpecIF:isUndirected: false
- SpecIF:Instantiation: auto

## sysml:extends (SpecIF:TermStatementClass)
- SpecIF:Revision: 1.2
- dcterms:description: An [[FMC:Actor]] «UseCase» extends another [[FMC:Actor]] «UseCase».
- SpecIF:Domain: SpecIF:DomainSystemModelIntegration
- SpecIF:TermStatus: SpecIF:LifecycleStatusEquivalent
- SpecIF:LocalTerm: extends
- SpecIF:isUndirected: false
- SpecIF:Instantiation: auto

## sysml:includes (SpecIF:TermStatementClass)
- SpecIF:Revision: 1.2
- dcterms:description: An [[FMC:Actor]] «UseCase» includes another [[FMC:Actor]] «UseCase».
- SpecIF:Domain: SpecIF:DomainSystemModelIntegration
- SpecIF:TermStatus: SpecIF:LifecycleStatusReleased
- SpecIF:LocalTerm: includes
- SpecIF:isUndirected: false
- SpecIF:Instantiation: auto

## uml:Realization (SpecIF:TermStatementClass)
- SpecIF:Revision: 1.2
- dcterms:description: A component *realizes' a function.
- SpecIF:Domain: SpecIF:DomainSystemsEngineering, SpecIF:DomainSystemModelIntegration
- SpecIF:TermStatus: SpecIF:LifecycleStatusReleased
- SpecIF:LocalTerm: realizes
- SpecIF:isUndirected: false
- SpecIF:Instantiation: auto

## uml:ownedBehavior (SpecIF:TermStatementClass)
- SpecIF:Revision: 1.2
- SpecIF:Domain: SpecIF:DomainSystemsEngineering, SpecIF:DomainSystemModelIntegration
- SpecIF:TermStatus: SpecIF:LifecycleStatusReleased
- SpecIF:LocalTerm: has Behavior
- SpecIF:isUndirected: false
- SpecIF:Instantiation: auto

## uml:Trigger (SpecIF:TermStatementClass)
- SpecIF:Revision: 1.2
- SpecIF:Domain: SpecIF:DomainSystemsEngineering, SpecIF:DomainSystemModelIntegration
- SpecIF:TermStatus: SpecIF:LifecycleStatusReleased
- SpecIF:LocalTerm: triggers
- SpecIF:isUndirected: false
- SpecIF:Instantiation: auto

## uml:TransitionSource (SpecIF:TermStatementClass)
- SpecIF:Revision: 1.2
- SpecIF:Domain: SpecIF:DomainSystemsEngineering, SpecIF:DomainSystemModelIntegration
- SpecIF:TermStatus: SpecIF:LifecycleStatusReleased
- SpecIF:LocalTerm: starts from
- SpecIF:isUndirected: false
- SpecIF:Instantiation: auto

## uml:TransitionTarget (SpecIF:TermStatementClass)
- SpecIF:Revision: 1.2
- SpecIF:Domain: SpecIF:DomainSystemsEngineering, SpecIF:DomainSystemModelIntegration
- SpecIF:TermStatus: SpecIF:LifecycleStatusReleased
- SpecIF:LocalTerm: ends at
- SpecIF:isUndirected: false
- SpecIF:Instantiation: auto

## uml:ControlFlow (SpecIF:TermStatementClass)
- SpecIF:Revision: 1.2
- SpecIF:Domain: SpecIF:DomainSystemsEngineering, SpecIF:DomainSystemModelIntegration
- SpecIF:TermStatus: SpecIF:LifecycleStatusEquivalent
- SpecIF:LocalTerm: UML Control Flow
- SpecIF:isUndirected: false
- SpecIF:Instantiation: auto

## SpecIF:isSpecializationOf (SpecIF:TermStatementClass)
- dcterms:description: A FMC:Actor is a specialization of another FMC:Actor; similarly for FMC:State and FMC:Event.
- SpecIF:Domain: SpecIF:DomainSystemModelIntegration
- SpecIF:TermStatus: SpecIF:LifecycleStatusReleased
- SpecIF:LocalTerm: specializes
- SpecIF:isUndirected: false
- SpecIF:Instantiation: auto

## SpecIF:isSpecializationOfResource (SpecIF:TermStatementClass)
- dcterms:identifier: SC-isSpecializationOfResource
- SpecIF:Revision: 1.2
- dcterms:description: A resource-class term is a specialization of another, such as 'Passenger Car' and 'Vehicle'.
- SpecIF:Domain: SpecIF:DomainOntology
- SpecIF:TermStatus: SpecIF:LifecycleStatusReleased
- SpecIF:LocalTerm: specializes
- SpecIF:isUndirected: false
- SpecIF:Instantiation: user

## SpecIF:isSpecializationOfStatement (SpecIF:TermStatementClass)
- dcterms:identifier: SC-isSpecializationOfStatement
- SpecIF:Revision: 1.2
- dcterms:description: A statement-class term is a specialization of another, such as 'is aggregated by' and 'contains'.
- SpecIF:Domain: SpecIF:DomainOntology
- SpecIF:TermStatus: SpecIF:LifecycleStatusReleased
- SpecIF:LocalTerm: specializes
- SpecIF:isUndirected: false
- SpecIF:Instantiation: user

## uml:Generalization (SpecIF:TermStatementClass)
- SpecIF:Revision: 1.2
- dcterms:description: A [[FMC:Actor]] is a generalization of another [[FMC:Actor]]; similarly for [[FMC:State]] and [[FMC:Event]].
- SpecIF:Domain: SpecIF:DomainSystemsEngineering, SpecIF:DomainSystemModelIntegration
- SpecIF:TermStatus: SpecIF:LifecycleStatusReleased
- SpecIF:LocalTerm: generalizes
- SpecIF:isUndirected: false
- SpecIF:Instantiation: auto

## SpecIF:isGeneralizationOfResource (SpecIF:TermStatementClass)
- dcterms:identifier: SC-isGeneralizationOfResource
- SpecIF:Revision: 1.2
- dcterms:description: A resource-class term is a generalization of another, such as 'Vehicle' and 'Passenger Car'.
- SpecIF:TermStatus: SpecIF:LifecycleStatusReleased
- SpecIF:LocalTerm: generalizes
- SpecIF:isUndirected: false
- SpecIF:Instantiation: user

## SpecIF:isGeneralizationOfStatement (SpecIF:TermStatementClass)
- dcterms:identifier: SC-isGeneralizationOfStatement
- SpecIF:Revision: 1.2
- dcterms:description: A statement-class term is a generalization of another, such as 'contains' and 'is aggregated by'.
- SpecIF:TermStatus: SpecIF:LifecycleStatusReleased
- SpecIF:LocalTerm: generalizes
- SpecIF:isUndirected: false
- SpecIF:Instantiation: user

## SpecIF:isGeneralizationOf (SpecIF:TermStatementClass)
- dcterms:description: A FMC:Actor is a generalization of another FMC:Actor; similarly for FMC:State and FMC:Event.
- SpecIF:TermStatus: SpecIF:LifecycleStatusEquivalent
- SpecIF:isUndirected: false
- SpecIF:Instantiation: auto

## SpecIF:inheritsFrom (SpecIF:TermStatementClass)
- dcterms:description: A model-element class inherits from another. For example a data-object of class [[FMC:State]] inherits from another data-object, as shown in a UML Class Diagram).
- SpecIF:TermStatus: SpecIF:LifecycleStatusReleased
- SpecIF:LocalTerm: inherits from
- SpecIF:isUndirected: false

## IR:inheritsFrom (SpecIF:TermStatementClass)
- dcterms:description: A model-element class inherits from another.
- SpecIF:TermStatus: SpecIF:LifecycleStatusEquivalent
- SpecIF:LocalTerm: inherits from
- SpecIF:isUndirected: false

## SpecIF:refersTo (SpecIF:TermStatementClass)
- dcterms:identifier: SC-refersTo
- SpecIF:Revision: 1.2
- dcterms:description: A resource 'refers to' any other resource.
- SpecIF:Domain: SpecIF:DomainBase
- SpecIF:TermStatus: SpecIF:LifecycleStatusReleased
- SpecIF:LocalTerm: refers to
- SpecIF:isUndirected: false

## IR:refersTo (SpecIF:TermStatementClass)
- dcterms:description: An Interaction-Room annotation 'refers to' any other model element.
- SpecIF:Domain: SpecIF:DomainSystemModelIntegration
- SpecIF:TermStatus: SpecIF:LifecycleStatusEquivalent
- SpecIF:LocalTerm: refers to
- SpecIF:isUndirected: false
- SpecIF:Instantiation: user

## IR:approves (SpecIF:TermStatementClass)
- SpecIF:Revision: 1.2
- SpecIF:Domain: SpecIF:DomainSystemModelIntegration
- SpecIF:TermStatus: SpecIF:LifecycleStatusReleased
- SpecIF:LocalTerm: supports
- SpecIF:isUndirected: false
- SpecIF:Instantiation: user

## IR:opposes (SpecIF:TermStatementClass)
- SpecIF:Revision: 1.2
- SpecIF:Domain: SpecIF:DomainSystemModelIntegration
- SpecIF:TermStatus: SpecIF:LifecycleStatusReleased
- SpecIF:LocalTerm: opposes
- SpecIF:isUndirected: false
- SpecIF:Instantiation: user

## SpecIF:commentRefersTo (SpecIF:TermStatementClass)
- dcterms:identifier: SC-commentRefersTo
- SpecIF:Revision: 1.2
- dcterms:description: A [[SpecIF:Comment]] 'refers to' a model element ('resource' in general).
- SpecIF:Domain: SpecIF:DomainBase, SpecIF:DomainOntology
- SpecIF:TermStatus: SpecIF:LifecycleStatusReleased
- SpecIF:LocalTerm: refers to
- SpecIF:isUndirected: false
- SpecIF:Instantiation: auto, user

## SpecIF:issueRefersTo (SpecIF:TermStatementClass)
- dcterms:identifier: SC-issueRefersTo
- SpecIF:Revision: 1.2
- dcterms:description: A [[SpecIF:Issue]] 'refers to' a model element ('resource' in general).
- SpecIF:Domain: SpecIF:DomainBase
- SpecIF:TermStatus: SpecIF:LifecycleStatusReleased
- SpecIF:LocalTerm: refers to
- SpecIF:isUndirected: false
- SpecIF:Instantiation: auto, user

## SpecIF:mentions (SpecIF:TermStatementClass)
- dcterms:description: A resource's text refers to another resource (e.g. by hyperlink).
- SpecIF:Domain: SpecIF:DomainBase
- SpecIF:TermStatus: SpecIF:LifecycleStatusReleased
- SpecIF:LocalTerm: mentions
- SpecIF:isUndirected: false

## SpecIF:isSynonymOf (SpecIF:TermStatementClass)
- SpecIF:Revision: 1.2
- dcterms:description: A term is synonymous with another term, if both represent the same concept.
  According to Wikipedia, a synonym is a word or phrase that means exactly or nearly the same as another word or phrase in the same language. Words that are synonyms are said to be synonymous.
- SpecIF:Domain: SpecIF:DomainOntology
- SpecIF:TermStatus: SpecIF:LifecycleStatusReleased
- SpecIF:LocalTerm: Synonym of
- SpecIF:isUndirected: true

## SpecIF:isSynonymOfResource (SpecIF:TermStatementClass)
- dcterms:identifier: SC-isSynonymOfResource
- SpecIF:Revision: 1.2
- dcterms:description: A resource-class term is synonymous with another.
- SpecIF:Domain: SpecIF:DomainOntology
- SpecIF:TermStatus: SpecIF:LifecycleStatusReleased
- SpecIF:LocalTerm: Synonym of
- SpecIF:isUndirected: true
- SpecIF:Instantiation: user

## SpecIF:isSynonymOfStatement (SpecIF:TermStatementClass)
- dcterms:identifier: SC-isSynonymOfStatement
- SpecIF:Revision: 1.2
- dcterms:description: A statement-class term is synonymous with another.
- SpecIF:Domain: SpecIF:DomainOntology
- SpecIF:TermStatus: SpecIF:LifecycleStatusReleased
- SpecIF:LocalTerm: Synonym of
- SpecIF:isUndirected: true
- SpecIF:Instantiation: user

## SpecIF:isSynonymOfProperty (SpecIF:TermStatementClass)
- dcterms:identifier: SC-isSynonymOfProperty
- SpecIF:Revision: 1.2
- dcterms:description: A property-class term is synonymous with another.

  Limitation: This statement is applicable for properties of all data types - the user must pay attention.
- SpecIF:Domain: SpecIF:DomainOntology
- SpecIF:TermStatus: SpecIF:LifecycleStatusReleased
- SpecIF:LocalTerm: Synonym of
- SpecIF:isUndirected: true
- SpecIF:Instantiation: user

## SpecIF:isSynonymOfValue (SpecIF:TermStatementClass)
- dcterms:identifier: SC-isSynonymOfValue
- SpecIF:Revision: 1.2
- dcterms:description: A value term is synonymous with another.

  Limitation: This statement is applicable for property values of all data types - the user must pay attention.
- SpecIF:Domain: SpecIF:DomainOntology
- SpecIF:TermStatus: SpecIF:LifecycleStatusReleased
- SpecIF:LocalTerm: Synonym of
- SpecIF:isUndirected: true
- SpecIF:Instantiation: user

## SpecIF:isInverseOf (SpecIF:TermStatementClass)
- dcterms:description: A term is the inverse of another term.
  For example, a system 'B' contains a component '11', thus '11' isContainedBy 'B'.
- SpecIF:TermStatus: SpecIF:LifecycleStatusDeprecated
- SpecIF:isUndirected: true

## SpecIF:isAntonymOf (SpecIF:TermStatementClass)
- SpecIF:Revision: 1.2
- dcterms:description: According to Wikipedia, the term antonym (and the related antonymy) is commonly taken to be synonymous with opposite, but antonym also has other more restricted meanings. Graded (or gradable) antonyms are word pairs whose meanings are opposite and which lie on a continuous spectrum (_hot_, _cold_). Complementary antonyms are word pairs whose meanings are opposite but whose meanings do not lie on a continuous spectrum (_push_, _pull_). Relational antonyms are word pairs where opposite makes sense only in the context of the relationship between the two meanings (_teacher_, _pupil_).
- SpecIF:Domain: SpecIF:DomainOntology
- SpecIF:TermStatus: SpecIF:LifecycleStatusReleased
- SpecIF:LocalTerm: Antonym of
- SpecIF:isUndirected: true

## SpecIF:isAntonymOfStatement (SpecIF:TermStatementClass)
- dcterms:identifier: SC-isAntonymOfStatement
- SpecIF:Revision: 1.2
- dcterms:description: A statement term is antonymous with another.
- SpecIF:Domain: SpecIF:DomainOntology
- SpecIF:TermStatus: SpecIF:LifecycleStatusReleased
- SpecIF:LocalTerm: Antonym of
- SpecIF:isUndirected: true
- SpecIF:Instantiation: user

## SpecIF:isAntonymOfValue (SpecIF:TermStatementClass)
- dcterms:identifier: SC-isAntonymOfValue
- SpecIF:Revision: 1.2
- dcterms:description: A value term is antonymous with another.
- SpecIF:Domain: SpecIF:DomainOntology
- SpecIF:TermStatus: SpecIF:LifecycleStatusReleased
- SpecIF:LocalTerm: Antonym of
- SpecIF:isUndirected: true
- SpecIF:Instantiation: user

## SpecIF:isPluralOf (SpecIF:TermStatementClass)
- SpecIF:Revision: 1.2
- SpecIF:Domain: SpecIF:DomainOntology
- SpecIF:TermStatus: SpecIF:LifecycleStatusReleased
- SpecIF:LocalTerm: Plural of
- SpecIF:isUndirected: false

## SpecIF:isPluralOfResource (SpecIF:TermStatementClass)
- dcterms:identifier: SC-isPluralOfResource
- SpecIF:Revision: 1.2
- SpecIF:Domain: SpecIF:DomainOntology
- SpecIF:TermStatus: SpecIF:LifecycleStatusReleased
- SpecIF:LocalTerm: Plural of
- SpecIF:isUndirected: false
- SpecIF:Instantiation: user

## owl:sameAs (SpecIF:TermStatementClass)
- SpecIF:Revision: 1.2
- dcterms:description: An owl:sameAs statement indicates that two URI references actually refer to the same thing: the individuals have the same 'identity'. (source: OWL)
- SpecIF:Domain: SpecIF:DomainSystemModelIntegration
- SpecIF:TermStatus: SpecIF:LifecycleStatusReleased
- SpecIF:LocalTerm: identical with
- SpecIF:isUndirected: true
- SpecIF:Instantiation: user

## SpecIF:sameAs (SpecIF:TermStatementClass)
- dcterms:description: A resource represents the same entity as another resource.
- SpecIF:TermStatus: SpecIF:LifecycleStatusEquivalent
- SpecIF:isUndirected: true

## SpecIF:isNamespace (SpecIF:TermStatementClass)
- dcterms:identifier: SC-isNamespace
- SpecIF:Revision: 1.2
- dcterms:description: A namespace includes a term.
- SpecIF:Domain: SpecIF:DomainOntology
- SpecIF:TermStatus: SpecIF:LifecycleStatusReleased
- SpecIF:LocalTerm: namespace for
- SpecIF:isUndirected: false
- SpecIF:Instantiation: user

## SpecIF:hasProperty (SpecIF:TermStatementClass)
- dcterms:identifier: SC-hasProperty
- SpecIF:Revision: 1.2
- dcterms:description: A resource or statement of this class has a property.
- SpecIF:Domain: SpecIF:DomainOntology
- SpecIF:TermStatus: SpecIF:LifecycleStatusReleased
- SpecIF:LocalTerm: has Property
- SpecIF:isUndirected: false
- SpecIF:Instantiation: user

## SpecIF:hasEnumValue (SpecIF:TermStatementClass)
- dcterms:identifier: SC-hasEnumValue
- SpecIF:Revision: 1.1
- dcterms:description: A property may have none, one or more enumerated values. The value may be an ontology term of a resourcClass, a statementClass or a propertyValue.
  Please note: This holds, if an enumerated value is defined by the ontology. In general, the SpecIF schema allows enumerated values of any data-type. In case of 'xs:string', not only ontology terms, but any string is allowed as value.
- SpecIF:Domain: SpecIF:DomainOntology
- SpecIF:TermStatus: SpecIF:LifecycleStatusReleased
- SpecIF:LocalTerm: has enumerated Value
- SpecIF:isUndirected: false
- SpecIF:Instantiation: user

## SpecIF:isEligibleAsSubject (SpecIF:TermStatementClass)
- dcterms:identifier: SC-isEligibleAsSubject
- SpecIF:Revision: 1.2
- dcterms:description: A resource-term or statement-term is eligible as a subject of a statement-term.

  Or concretely: A resource or statement of this class is eligible as the statement's subject.
- SpecIF:Domain: SpecIF:DomainOntology
- SpecIF:TermStatus: SpecIF:LifecycleStatusReleased
- SpecIF:LocalTerm: eligible as Subject
- SpecIF:isUndirected: false
- SpecIF:Instantiation: user

## SpecIF:isEligibleAsObject (SpecIF:TermStatementClass)
- dcterms:identifier: SC-isEligibleAsObject
- SpecIF:Revision: 1.2
- dcterms:description: A resource-term or statement-term is eligible as an object of a predicate-term.

  Or concretely: A resource or statement of this class is eligible as the predicate's object.
- SpecIF:Domain: SpecIF:DomainOntology
- SpecIF:TermStatus: SpecIF:LifecycleStatusReleased
- SpecIF:LocalTerm: eligible as Object
- SpecIF:isUndirected: false
- SpecIF:Instantiation: user

## DDP:definedBy (SpecIF:TermStatementClass)
- SpecIF:Revision: 1.2
- SpecIF:Domain: SpecIF:DomainSystemModelIntegration
- SpecIF:LocalTerm: defined by
- SpecIF:isUndirected: false
- SpecIF:Instantiation: auto, user

## Property Class Terms (SpecIF:Heading)
- dcterms:description: A property carries information 'payload' and may be applied to resources or statements. The SpecIF terms listed in this chapter are used as property name/title, whereas the information is provided as 'value'. Usually a combination of complimentary properties is used per resource or statement class.
  A property corresponds to an 'ATTRIBUTE-DEFINITION' resp. 'ATTRIBUTE-VALUE' in the Requirements Interchange Format (ReqIF).

## dcterms:identifier (SpecIF:TermPropertyClassString)
- dcterms:identifier: PC-VisibleId
- SpecIF:Revision: 1.1
- dcterms:description: A unique reference to the resource within a given context. (source: DCMI)
  An identifier for a resource. This identifier may be unique with a scope that is defined by the RM provider. Assigned by the service provider when a resource is created. Not intended for end-user display. (source: OSLC)
- SpecIF:Domain: SpecIF:DomainBase
- SpecIF:TermStatus: SpecIF:LifecycleStatusReleased
- SpecIF:LocalTerm: Identifier
- SpecIF:isRequired: false
- SpecIF:multiple: false
- SpecIF:singleLanguage: true
- SpecIF:TextFormat: plain
- SpecIF:StringMaxLength: 256

## ReqIF.ForeignID (SpecIF:TermPropertyClassString)
- SpecIF:Revision: 1.2
- dcterms:description: The original identifier of the resource ('object' in terms of ReqIF).
- SpecIF:Domain: SpecIF:DomainRequirementsEngineeringSRC
- SpecIF:TermStatus: SpecIF:LifecycleStatusEquivalent
- SpecIF:LocalTerm: Original ID
- SpecIF:isRequired: false
- SpecIF:multiple: false
- SpecIF:singleLanguage: true
- SpecIF:TextFormat: plain
- SpecIF:StringMaxLength: 32

## dcterms:title (SpecIF:TermPropertyClassString)
- dcterms:identifier: PC-Name
- SpecIF:Revision: 1.1
- dcterms:description: A name given to the resource. (source: DCMI)
  Title (reference: Dublin Core) of the resource represented as rich text in XHTML content. SHOULD include only content that is valid inside an XHTML 'span' element. (source: OSLC)
- SpecIF:LocalTerm: Title
- SpecIF:Domain: SpecIF:DomainBase
- SpecIF:TermStatus: SpecIF:LifecycleStatusReleased
- SpecIF:multiple: false
- SpecIF:TextFormat: plain
- SpecIF:StringMaxLength: 256

## rdfs:label (SpecIF:TermPropertyClassString)
- dcterms:description: rdfs:label is an instance of rdf:Property that may be used to provide a human-readable version of a resource's name.
  A triple of the form:
  R rdfs:label L
  states that L is a human readable label for R.
  The rdfs:domain of rdfs:label is rdfs:Resource. The rdfs:range of rdfs:label is rdfs:Literal.
  Multilingual labels are supported using the language tagging facility of RDF literals.
- SpecIF:Domain: SpecIF:DomainSystemModelIntegration
- SpecIF:TermStatus: SpecIF:LifecycleStatusEquivalent
- SpecIF:LocalTerm: Label
- SpecIF:isRequired: false
- SpecIF:multiple: false

## schema:name (SpecIF:TermPropertyClassString)
- SpecIF:Revision: 1.2
- dcterms:description: The name of the item.
- SpecIF:Domain: SpecIF:DomainBase
- SpecIF:TermStatus: SpecIF:LifecycleStatusReleased
- SpecIF:LocalTerm: Name
- SpecIF:multiple: false
- SpecIF:TextFormat: plain
- SpecIF:StringMaxLength: 256

## SpecIF:Term (SpecIF:TermPropertyClassString)
- dcterms:identifier: PC-SpecifTerm
- SpecIF:Revision: 1.2
- dcterms:description: A name given to an ontology term.
- SpecIF:Domain: SpecIF:DomainOntology
- SpecIF:TermStatus: SpecIF:LifecycleStatusReleased
- SpecIF:LocalTerm: Term
- SpecIF:isRequired: false
- SpecIF:multiple: false
- SpecIF:singleLanguage: true
- SpecIF:TextFormat: plain
- SpecIF:StringMaxLength: 256

## ReqIF.Name (SpecIF:TermPropertyClassString)
- SpecIF:Revision: 1.2
- SpecIF:LocalTerm: Name
- SpecIF:Domain: SpecIF:DomainBase, SpecIF:DomainRequirementsEngineeringSRC
- SpecIF:TermStatus: SpecIF:LifecycleStatusEquivalent
- SpecIF:multiple: false
- SpecIF:TextFormat: xhtml
- SpecIF:StringMaxLength: 256

## ReqIF.ChapterName (SpecIF:TermPropertyClassString)
- SpecIF:Revision: 1.2
- SpecIF:Domain: SpecIF:DomainRequirementsEngineeringSRC
- SpecIF:TermStatus: SpecIF:LifecycleStatusSubmitted
- SpecIF:LocalTerm: Chapter Title
- SpecIF:multiple: false
- SpecIF:TextFormat: xhtml
- SpecIF:StringMaxLength: 256

## ReqIF.ChapterNumber (SpecIF:TermPropertyClassString)
- SpecIF:Revision: 1.2
- SpecIF:Domain: SpecIF:DomainRequirementsEngineeringSRC
- SpecIF:TermStatus: SpecIF:LifecycleStatusSubmitted
- SpecIF:LocalTerm: Chapter Number
- SpecIF:multiple: false
- SpecIF:TextFormat: plain
- SpecIF:StringMaxLength: 32

## dcterms:description (SpecIF:TermPropertyClassString)
- dcterms:identifier: PC-Description
- SpecIF:Revision: 1.1
- dcterms:description: An account of the resource. (source: DCMI)
  Descriptive text (reference: Dublin Core) about resource represented as rich text in XHTML content. SHOULD include only content that is valid and suitable inside an XHTML 'div' element. (source: OSLC)
- SpecIF:LocalTerm: Description
- SpecIF:Domain: SpecIF:DomainBase
- SpecIF:TermStatus: SpecIF:LifecycleStatusReleased
- SpecIF:multiple: false
- SpecIF:TextFormat: xhtml

## rdfs:comment (SpecIF:TermPropertyClassString)
- dcterms:description: rdfs:comment is an instance of rdf:Property that may be used to provide a human-readable description of a resource.
  A triple of the form:
  R rdfs:comment L
  states that L is a human readable description of R.
  The rdfs:domain of rdfs:comment is rdfs:Resource. The rdfs:range of rdfs:comment is rdfs:Literal.
  A textual comment helps clarify the meaning of RDF classes and properties. Such in-line documentation complements the use of both formal techniques (Ontology and rule languages) and informal (prose documentation, examples, test cases). A variety of documentation forms can be combined to indicate the intended meaning of the classes and properties described in an RDF vocabulary. Since RDF vocabularies are expressed as RDF graphs, vocabularies defined in other namespaces may be used to provide richer documentation.
  Multilingual documentation is supported through use of the language tagging facility of RDF literals.
- SpecIF:Domain: SpecIF:DomainSystemModelIntegration
- SpecIF:TermStatus: SpecIF:LifecycleStatusEquivalent
- SpecIF:LocalTerm: Comment
- SpecIF:isRequired: false
- SpecIF:multiple: false
- SpecIF:TextFormat: xhtml

## schema:description (SpecIF:TermPropertyClassString)
- SpecIF:Revision: 1.2
- dcterms:description: A description of the item.
- SpecIF:Domain: SpecIF:DomainBase
- SpecIF:TermStatus: SpecIF:LifecycleStatusEquivalent
- SpecIF:LocalTerm: Description
- SpecIF:multiple: false
- SpecIF:TextFormat: xhtml

## ReqIF.Text (SpecIF:TermPropertyClassString)
- SpecIF:Revision: 1.2
- SpecIF:LocalTerm: Description, Text, Object Text
- SpecIF:Domain: SpecIF:DomainRequirementsEngineeringSRC
- SpecIF:TermStatus: SpecIF:LifecycleStatusEquivalent
- SpecIF:multiple: false
- SpecIF:TextFormat: xhtml

## dcterms:type (SpecIF:TermPropertyClassString)
- dcterms:identifier: PC-Type
- SpecIF:Revision: 1.1
- dcterms:description: The nature or genre of the resource. (source: DCMI)
  Recommended best practice is to use a controlled vocabulary such as the DCMI Type Vocabulary [DCMITYPE]. To describe the file format, physical medium, or dimensions of the resource, use the Format element.
  For example, a [[FMC:Actor]] may represent a System Function, a System Component or a User Role. Similarly, in the context of process modelling, a FMC:Actor may represent a Process Step or again a User Role. So, all of these are meaningful values for a FMC:Actor's property named dcterms:type.
- SpecIF:Domain: SpecIF:DomainBase
- SpecIF:TermStatus: SpecIF:LifecycleStatusReleased
- SpecIF:LocalTerm: Element Type
- SpecIF:isRequired: false
- SpecIF:multiple: false
- SpecIF:singleLanguage: true
- SpecIF:TextFormat: plain
- SpecIF:StringMaxLength: 32

## SpecIF:Type (SpecIF:TermPropertyClassString)
- SpecIF:TermStatus: SpecIF:LifecycleStatusDeprecated
- SpecIF:multiple: false

## SpecIF:ModelFile (SpecIF:TermPropertyClassString)
- SpecIF:Revision: 1.2
- dcterms:description: A file with partial model information.
- SpecIF:Domain: SpecIF:DomainRequirementsEngineering, SpecIF:DomainRequirementsEngineeringSRC, SpecIF:DomainSystemModelIntegration
- SpecIF:TermStatus: SpecIF:LifecycleStatusSubmitted
- SpecIF:LocalTerm: Model File
- SpecIF:multiple: false
- SpecIF:TextFormat: xhtml
- SpecIF:StringMaxLength: 256

## ReqIF.Category (SpecIF:TermPropertyClassString)
- SpecIF:Revision: 1.2
- SpecIF:LocalTerm: Category
- SpecIF:Domain: SpecIF:DomainSystemModelIntegration
- SpecIF:TermStatus: SpecIF:LifecycleStatusEquivalent
- SpecIF:multiple: false
- SpecIF:TextFormat: plain
- SpecIF:StringMaxLength: 256

## SpecIF:Diagram (SpecIF:TermPropertyClassString)
- dcterms:identifier: PC-Diagram
- SpecIF:Revision: 1.1
- dcterms:description: One or more diagrams illustrating the resource.
- SpecIF:LocalTerm: Diagram, Plan
- SpecIF:Domain: SpecIF:DomainBase, SpecIF:DomainRequirementsEngineering, SpecIF:DomainRequirementsEngineeringSRC, SpecIF:DomainSystemModelIntegration
- SpecIF:TermStatus: SpecIF:LifecycleStatusReleased
- SpecIF:multiple: true
- SpecIF:TextFormat: xhtml

## SpecIF:Notation (SpecIF:TermPropertyClassString)
- dcterms:identifier: PC-Notation
- SpecIF:Revision: 1.2
- dcterms:description: The notation used by a model diagram, e.g. 'BPMN 2.0', 'SysML Activity Diagram' or 'FMC Block Diagram'.
- SpecIF:Domain: SpecIF:DomainSystemModelIntegration
- SpecIF:TermStatus: SpecIF:LifecycleStatusReleased
- SpecIF:LocalTerm: Notation
- SpecIF:multiple: false
- SpecIF:TextFormat: plain
- SpecIF:StringMaxLength: 32

## SpecIF:Category (SpecIF:TermPropertyClassString)
- dcterms:description: The 'Category' (class) of the resource, usually with an enumerated value.
  Useful categories for requirements have been defined by the IREB, namely 'Function', 'Quality' and 'Constraint'.
- SpecIF:TermStatus: SpecIF:LifecycleStatusEquivalent
- SpecIF:LocalTerm: Category

## SpecIF:Id (SpecIF:TermPropertyClassString)
- dcterms:description: A unique reference to the resource within a given context.
- SpecIF:TermStatus: SpecIF:LifecycleStatusDeprecated

## SpecIF:Index (SpecIF:TermPropertyClassInteger)
- SpecIF:Revision: 1.2
- SpecIF:Domain: SpecIF:DomainOntology
- SpecIF:TermStatus: SpecIF:LifecycleStatusReleased
- SpecIF:LocalTerm: Index
- SpecIF:isRequired: false
- SpecIF:multiple: false
- SpecIF:IntegerMinInclusive: 0
- SpecIF:IntegerMaxInclusive: 2147483647

## dcterms:subject (SpecIF:TermPropertyClassString)
- dcterms:description: The topic of the resource. (source: DCMI)
  Tag or keyword for a resource. Each occurrence of a dcterms:subject property denotes an additional tag for the resource. (source: OSLC)
- SpecIF:TermStatus: SpecIF:LifecycleStatusReleased
- SpecIF:LocalTerm: Subject
- SpecIF:multiple: false

## dcterms:source (SpecIF:TermPropertyClassString)
- dcterms:description: A related resource from which the described resource is derived. (source: DCMI)
  The described resource may be derived from the related resource in whole or in part. Recommended best practice is to identify the related resource by means of a string conforming to a formal identification system.
- SpecIF:TermStatus: SpecIF:LifecycleStatusReleased
- SpecIF:LocalTerm: Source
- SpecIF:multiple: false
- SpecIF:TextFormat: plain
- SpecIF:StringMaxLength: 32

## dcterms:creator (SpecIF:TermPropertyClassString)
- dcterms:description: An entity primarily responsible for making the resource. (source: DCMI)
  Creator(s) of resource (reference: Dublin Core). It is likely that the target resource will be a [[foaf:Person]] but that is not necessarily the case. (source: OSLC)
- SpecIF:TermStatus: SpecIF:LifecycleStatusReleased
- SpecIF:LocalTerm: created by, Author
- SpecIF:multiple: false

## SpecIF:createdBy (SpecIF:TermPropertyClassString)
- dcterms:description: A resource primarily responsible for making the resource.
- SpecIF:TermStatus: SpecIF:LifecycleStatusEquivalent

## dcterms:created (SpecIF:TermPropertyClassTimestamp)
- dcterms:description: Timestamp of resource creation. (source: DCMI)
- SpecIF:TermStatus: SpecIF:LifecycleStatusReleased
- SpecIF:LocalTerm: created at
- SpecIF:multiple: false

## SpecIF:createdAt (SpecIF:TermPropertyClassTimestamp)
- dcterms:description: Date/time of creation of the resource.
- SpecIF:TermStatus: SpecIF:LifecycleStatusEquivalent
- SpecIF:LocalTerm: created at
- SpecIF:multiple: false

## SpecIF:changedBy (SpecIF:TermPropertyClassString)
- dcterms:description: The author who made the last modification.
- SpecIF:LocalTerm: changed by
- SpecIF:TermStatus: SpecIF:LifecycleStatusReleased

## dcterms:modified (SpecIF:TermPropertyClassTimestamp)
- dcterms:description: Timestamp last latest resource modification. (source: DCMI)
- SpecIF:TermStatus: SpecIF:LifecycleStatusReleased
- SpecIF:LocalTerm: changed at
- SpecIF:multiple: false

## SpecIF:changedAt (SpecIF:TermPropertyClassTimestamp)
- dcterms:description: Date/time on which the resource was changed last.
- SpecIF:TermStatus: SpecIF:LifecycleStatusEquivalent
- SpecIF:LocalTerm: changed at
- SpecIF:multiple: false

## dcterms:contributor (SpecIF:TermPropertyClassString)
- dcterms:description: A resource responsible for making contributions to the resource. (source: DCMI)
- SpecIF:TermStatus: SpecIF:LifecycleStatusReleased
- SpecIF:LocalTerm: Contributor
- SpecIF:multiple: false

## dcterms:rightsHolder (SpecIF:TermPropertyClassString)
- dcterms:description: A person or organization owning or managing rights over the resource. (source: DCMI)
- SpecIF:TermStatus: SpecIF:LifecycleStatusReleased
- SpecIF:LocalTerm: Rights Holder

## dcterms:rights (SpecIF:TermPropertyClassString)
- dcterms:description: Information about rights held in and over the resource. (source: DCMI)
- SpecIF:TermStatus: SpecIF:LifecycleStatusReleased
- SpecIF:LocalTerm: Rights

## oslc:shortTitle (SpecIF:TermPropertyClassString)
- dcterms:description: Short name identifying a resource, often used as an abbreviated identifier for presentation to end-users. SHOULD include only content that is valid inside an XHTML 'span' element.

## oslc:serviceProvider (SpecIF:TermPropertyClassString)
- dcterms:description: The scope of a resource is a URI for the resource's OSLC Service Provider.
- SpecIF:Domain: SpecIF:DomainSystemModelIntegration
- SpecIF:TermStatus: SpecIF:LifecycleStatusSubmitted
- SpecIF:LocalTerm: Service Provider
- SpecIF:multiple: false

## oslc:instanceShape (SpecIF:TermPropertyClassString)
- dcterms:description: Resource Shape that provides hints as to resource property value-types and allowed values.

## SpecIF:Stereotype (SpecIF:TermPropertyClassString)
- dcterms:description: Describes the role or sub-type of a model-element. For example, a [[FMC:Actor]] may represent a System Function, a System Component or a User Role. Similarly, in the context of process modelling, a FMC:Actor may represent a Process Step or again a User Role. So, all of these are meaningful values for a FMC:Actor's property named SpecIF:Stereotype.
- SpecIF:TermStatus: SpecIF:LifecycleStatusDeprecated

## uml:Stereotype (SpecIF:TermPropertyClassString)
- dcterms:description: Describes the role or sub-type of a model-element. For example, a [[FMC:Actor]] may represent a System Function, a System Component or a User Role. Similarly, in the context of process modelling, a FMC:Actor may represent a Process Step or again a User Role. So, all of these are meaningful values for a FMC:Actor's property named uml:Stereotype.
- SpecIF:LocalTerm: Stereotype
- SpecIF:TermStatus: SpecIF:LifecycleStatusReleased

## uml:is_Service (SpecIF:TermPropertyClassBoolean)
- SpecIF:Revision: 1.2
- SpecIF:Domain: SpecIF:DomainSystemsEngineering, SpecIF:DomainSystemModelIntegration
- SpecIF:TermStatus: SpecIF:LifecycleStatusReleased
- SpecIF:LocalTerm: is server
- SpecIF:isRequired: false
- SpecIF:multiple: false
- SpecIF:DefaultValueBoolean: false

## uml:Flow_Direction (SpecIF:TermPropertyClassString)
- SpecIF:Revision: 1.2
- SpecIF:Domain: SpecIF:DomainSystemsEngineering, SpecIF:DomainSystemModelIntegration
- SpecIF:TermStatus: SpecIF:LifecycleStatusReleased
- SpecIF:LocalTerm: Flow Direction
- SpecIF:isRequired: false
- SpecIF:multiple: false
- SpecIF:TextFormat: plain
- SpecIF:StringMaxLength: 32

## IREB:RequirementType (SpecIF:TermPropertyClassString)
- dcterms:identifier: PC-RequirementType
- SpecIF:Revision: 1.2
- dcterms:description: According to the IREB, requirements are typically classified into functional requirements ([[IREB:FunctionalRequirement]]), quality requirements ([[IREB:QualityRequirement]]) and constraints ([[IREB:Constraint]]). The latter two are also called non-functional requirements.
- SpecIF:Domain: SpecIF:DomainRequirementsEngineering
- SpecIF:TermStatus: SpecIF:LifecycleStatusExperimental
- SpecIF:LocalTerm: Type
- SpecIF:multiple: false
- SpecIF:TextFormat: plain
- SpecIF:StringMaxLength: 32

## SpecIF:SubClass (SpecIF:TermPropertyClassString)
- dcterms:description: Describes the role or sub-type of a model-element. For example, a [[FMC:Actor]] may represent a System Function, a System Component or a User Role. Similarly, in the context of process modelling, a FMC:Actor may represent a Process Step or again a User Role. So, all of these are meaningful values for a FMC:Actor's property named SpecIF:SubClass.
- SpecIF:TermStatus: SpecIF:LifecycleStatusDeprecated

## SpecIF:LifecycleStatus (SpecIF:TermPropertyClassString)
- dcterms:identifier: PC-LifecycleStatus
- SpecIF:Revision: 1.2
- dcterms:description: The 'Lifecycle Status' of the resource.
- SpecIF:Domain: SpecIF:DomainBase, SpecIF:DomainRequirementsEngineering, SpecIF:DomainRequirementsEngineeringSRC, SpecIF:DomainSystemModelIntegration
- SpecIF:TermStatus: SpecIF:LifecycleStatusReleased
- SpecIF:LocalTerm: Lifecycle
- SpecIF:multiple: false
- SpecIF:TextFormat: plain
- SpecIF:StringMaxLength: 32

## SpecIF:Status (SpecIF:TermPropertyClassString)
- dcterms:description: The 'Status' of the resource.
- SpecIF:TermStatus: SpecIF:LifecycleStatusDeprecated
- SpecIF:LocalTerm: Lifecycle
- SpecIF:isRequired: false
- SpecIF:multiple: false
- SpecIF:TextFormat: plain
- SpecIF:StringMaxLength: 32

## SpecIF:TermStatus (SpecIF:TermPropertyClassString)
- dcterms:identifier: PC-TermStatus
- SpecIF:Revision: 1.2
- dcterms:description: The lifecycle status of the ontology term.
- SpecIF:Domain: SpecIF:DomainOntology
- SpecIF:TermStatus: SpecIF:LifecycleStatusReleased
- SpecIF:LocalTerm: Lifecycle
- SpecIF:multiple: false
- SpecIF:TextFormat: plain
- SpecIF:StringMaxLength: 32

## ReqIF.ForeignState (SpecIF:TermPropertyClassString)
- SpecIF:Revision: 1.2
- SpecIF:LocalTerm: Original Status
- dcterms:description: The 'Lifecycle Status' of the resource.
- SpecIF:Domain: SpecIF:DomainRequirementsEngineeringSRC
- SpecIF:TermStatus: SpecIF:LifecycleStatusEquivalent
- SpecIF:multiple: false
- SpecIF:TextFormat: plain
- SpecIF:StringMaxLength: 32

## ReqIF.ForeignCreatedBy (SpecIF:TermPropertyClassString)
- SpecIF:Revision: 1.2
- SpecIF:Domain: SpecIF:DomainRequirementsEngineeringSRC
- SpecIF:TermStatus: SpecIF:LifecycleStatusEquivalent
- SpecIF:LocalTerm: Author
- SpecIF:multiple: false
- SpecIF:TextFormat: plain
- SpecIF:StringMaxLength: 32

## ReqIF.ForeignCreatedOn (SpecIF:TermPropertyClassString)
- SpecIF:Revision: 1.2
- SpecIF:Domain: SpecIF:DomainRequirementsEngineeringSRC
- SpecIF:TermStatus: SpecIF:LifecycleStatusEquivalent
- SpecIF:LocalTerm: created on
- SpecIF:multiple: false
- SpecIF:TextFormat: plain
- SpecIF:StringMaxLength: 32

## ReqIF.ForeignCreatedThru (SpecIF:TermPropertyClassString)
- SpecIF:Revision: 1.2
- SpecIF:LocalTerm: created through
- SpecIF:Domain: SpecIF:DomainRequirementsEngineeringSRC
- SpecIF:TermStatus: SpecIF:LifecycleStatusExperimental
- SpecIF:multiple: false
- SpecIF:TextFormat: plain
- SpecIF:StringMaxLength: 32

## ReqIF.ForeignModifiedBy (SpecIF:TermPropertyClassString)
- SpecIF:Revision: 1.2
- SpecIF:Domain: SpecIF:DomainRequirementsEngineeringSRC
- SpecIF:TermStatus: SpecIF:LifecycleStatusEquivalent
- SpecIF:LocalTerm: modified by
- SpecIF:multiple: false
- SpecIF:TextFormat: plain
- SpecIF:StringMaxLength: 32

## ReqIF.ForeignModifiedOn (SpecIF:TermPropertyClassString)
- SpecIF:Revision: 1.2
- SpecIF:Domain: SpecIF:DomainRequirementsEngineeringSRC
- SpecIF:TermStatus: SpecIF:LifecycleStatusEquivalent
- SpecIF:LocalTerm: modified on
- SpecIF:multiple: false
- SpecIF:TextFormat: plain
- SpecIF:StringMaxLength: 32

## ReqIF.Revision (SpecIF:TermPropertyClassString)
- SpecIF:Revision: 1.2
- SpecIF:Domain: SpecIF:DomainRequirementsEngineeringSRC
- SpecIF:TermStatus: SpecIF:LifecycleStatusEquivalent
- SpecIF:LocalTerm: Revision
- SpecIF:multiple: false
- SpecIF:TextFormat: plain
- SpecIF:StringMaxLength: 32

## ReqIF.Prefix (SpecIF:TermPropertyClassString)
- SpecIF:Revision: 1.2
- SpecIF:Domain: SpecIF:DomainRequirementsEngineeringSRC
- SpecIF:TermStatus: SpecIF:LifecycleStatusSubmitted
- SpecIF:LocalTerm: Prefix
- SpecIF:multiple: false
- SpecIF:TextFormat: plain
- SpecIF:StringMaxLength: 32

## ReqIF.Description (SpecIF:TermPropertyClassString)
- SpecIF:Revision: 1.2
- dcterms:description: According to the ReqIF Implementation Guide issued by prostep IVIP, this term is equivalent to ReqIF.Text, but none of the well known authoring tools uses it. Therefore the lifecycle status is set to 'experimental'.
- SpecIF:Domain: SpecIF:DomainRequirementsEngineeringSRC
- SpecIF:TermStatus: SpecIF:LifecycleStatusExperimental
- SpecIF:LocalTerm: Description
- SpecIF:multiple: false
- SpecIF:TextFormat: xhtml

## ReqIF.FitCriteria (SpecIF:TermPropertyClassString)
- SpecIF:Revision: 1.2
- SpecIF:Domain: SpecIF:DomainRequirementsEngineeringSRC
- SpecIF:TermStatus: SpecIF:LifecycleStatusEquivalent
- SpecIF:LocalTerm: Fit Criteria
- SpecIF:multiple: false
- SpecIF:TextFormat: xhtml

## ReqIF.ChangeDescription (SpecIF:TermPropertyClassString)
- SpecIF:Revision: 1.2
- SpecIF:Domain: SpecIF:DomainRequirementsEngineeringSRC
- SpecIF:TermStatus: SpecIF:LifecycleStatusSubmitted
- SpecIF:LocalTerm: Change Description
- SpecIF:multiple: false
- SpecIF:TextFormat: xhtml

## ReqIF.Project (SpecIF:TermPropertyClassString)
- SpecIF:Revision: 1.2
- SpecIF:Domain: SpecIF:DomainRequirementsEngineeringSRC
- SpecIF:TermStatus: SpecIF:LifecycleStatusSubmitted
- SpecIF:LocalTerm: Project
- SpecIF:multiple: false
- SpecIF:TextFormat: xhtml

## ReqIF.AssociatedFiles (SpecIF:TermPropertyClassString)
- SpecIF:Revision: 1.2
- SpecIF:Domain: SpecIF:DomainRequirementsEngineeringSRC
- SpecIF:TermStatus: SpecIF:LifecycleStatusSubmitted
- SpecIF:LocalTerm: Attachments
- SpecIF:multiple: false
- SpecIF:TextFormat: xhtml

## SpecIF:Revision (SpecIF:TermPropertyClassString)
- SpecIF:Revision: 1.2
- SpecIF:Domain: SpecIF:DomainRequirementsEngineeringSRC, SpecIF:DomainSystemModelIntegration
- SpecIF:LocalTerm: Revision
- SpecIF:TermStatus: SpecIF:LifecycleStatusReleased
- SpecIF:multiple: false
- SpecIF:TextFormat: plain
- SpecIF:StringMaxLength: 32

## SpecIF:Domain (SpecIF:TermPropertyClassString)
- dcterms:identifier: PC-Domain
- SpecIF:Revision: 1.2
- SpecIF:Domain: SpecIF:DomainOntology
- SpecIF:TermStatus: SpecIF:LifecycleStatusReleased
- SpecIF:LocalTerm: Domain
- SpecIF:isRequired: false
- SpecIF:multiple: true
- SpecIF:TextFormat: plain
- SpecIF:StringMaxLength: 32

## SpecIF:LocalTerm (SpecIF:TermPropertyClassString)
- SpecIF:Revision: 1.2
- dcterms:description: A name of the resource used in one or more national languages. Multiple values can be defined so that different local terms can be transformed ('globalized') to the ontology term.
- SpecIF:LocalTerm: Local Term
- SpecIF:Domain: SpecIF:DomainOntology
- SpecIF:TermStatus: SpecIF:LifecycleStatusReleased
- SpecIF:multiple: true
- SpecIF:TextFormat: plain
- SpecIF:StringMaxLength: 256

## SpecIF:LocalTermPlural (SpecIF:TermPropertyClassString)
- SpecIF:Revision: 1.2
- dcterms:description: A name of the resource in plural form used in one or more national languages. Multiple values can be defined so that different local terms can be transformed ('globalized') to the ontology term.
- SpecIF:Domain: SpecIF:DomainOntology
- SpecIF:TermStatus: SpecIF:LifecycleStatusReleased
- SpecIF:LocalTerm: Local Term (Plural)
- SpecIF:multiple: true
- SpecIF:TextFormat: plain
- SpecIF:StringMaxLength: 256

## SpecIF:Probability (SpecIF:TermPropertyClassReal)
- SpecIF:TermStatus: SpecIF:LifecycleStatusReleased
- SpecIF:LocalTerm: Probability
- SpecIF:multiple: false
- SpecIF:RealMinInclusive: 0
- SpecIF:RealMaxInclusive: 1.0
- SpecIF:RealFractionDigits: 2

## SpecIF:Impact (SpecIF:TermPropertyClassReal)
- SpecIF:Domain: SpecIF:DomainSystemModelIntegration
- SpecIF:TermStatus: SpecIF:LifecycleStatusSubmitted
- SpecIF:LocalTerm: Impact
- SpecIF:multiple: false
- SpecIF:Unit: €
- SpecIF:RealMinInclusive: 0.00
- SpecIF:RealFractionDigits: 2

## SpecIF:Priority (SpecIF:TermPropertyClassString)
- dcterms:identifier: PC-Priority
- SpecIF:Revision: 1.2
- SpecIF:LocalTerm: Priority
- dcterms:description: Enumerated values for the 'Priority' of the resource.
- SpecIF:Domain: SpecIF:DomainRequirementsEngineering, SpecIF:DomainRequirementsEngineeringSRC, SpecIF:DomainSystemModelIntegration
- SpecIF:TermStatus: SpecIF:LifecycleStatusReleased
- SpecIF:multiple: false
- SpecIF:TextFormat: plain
- SpecIF:StringMaxLength: 32

## SpecIF:Size (SpecIF:TermPropertyClassString)
- SpecIF:Revision: 1.2
- dcterms:description: Enumerated values for the 'Priority' of the resource.
- SpecIF:Domain: SpecIF:DomainRequirementsEngineering, SpecIF:DomainRequirementsEngineeringSRC, SpecIF:DomainSystemModelIntegration
- SpecIF:TermStatus: SpecIF:LifecycleStatusReleased
- SpecIF:LocalTerm: Size
- SpecIF:multiple: false
- SpecIF:TextFormat: plain
- SpecIF:StringMaxLength: 32

## SpecIF:Effort (SpecIF:TermPropertyClassString)
- SpecIF:Domain: SpecIF:DomainRequirementsEngineering, SpecIF:DomainRequirementsEngineeringSRC, SpecIF:DomainSystemModelIntegration
- SpecIF:TermStatus: SpecIF:LifecycleStatusReleased
- SpecIF:LocalTerm: Effort
- SpecIF:multiple: false
- SpecIF:TextFormat: plain
- SpecIF:StringMaxLength: 32

## SpecIF:Rationale (SpecIF:TermPropertyClassString)
- SpecIF:Domain: SpecIF:DomainRequirementsEngineering, SpecIF:DomainRequirementsEngineeringSRC, SpecIF:DomainSystemModelIntegration
- SpecIF:TermStatus: SpecIF:LifecycleStatusSubmitted
- SpecIF:LocalTerm: Rationale
- SpecIF:multiple: false
- SpecIF:TextFormat: plain

## SpecIF:EngineeringDiscipline (SpecIF:TermPropertyClassString)
- dcterms:identifier: PC-Discipline
- SpecIF:Revision: 1.2
- dcterms:description: The engineering discipline involved by a development artefact.
- SpecIF:Domain: SpecIF:DomainRequirementsEngineering, SpecIF:DomainRequirementsEngineeringSRC, SpecIF:DomainSystemModelIntegration
- SpecIF:TermStatus: SpecIF:LifecycleStatusReleased
- SpecIF:LocalTerm: Engineering Discipline
- SpecIF:multiple: true
- SpecIF:TextFormat: plain
- SpecIF:StringMaxLength: 32

## SpecIF:Discipline (SpecIF:TermPropertyClassString)
- dcterms:description: The engineering discipline involved by a development artefact.
- SpecIF:TermStatus: SpecIF:LifecycleStatusDeprecated
- SpecIF:LocalTerm: Engineering Discipline
- SpecIF:isRequired: false
- SpecIF:multiple: true
- SpecIF:TextFormat: plain
- SpecIF:StringMaxLength: 32

## SpecIF:StakeholderGroup (SpecIF:TermPropertyClassString)
- SpecIF:Revision: 1.2
- dcterms:description: Enumerated values for the 'Stakehoder Group' addressed by the term.
- SpecIF:Domain: SpecIF:DomainRequirementsEngineering, SpecIF:DomainRequirementsEngineeringSRC, SpecIF:DomainSystemModelIntegration
- SpecIF:TermStatus: SpecIF:LifecycleStatusReleased
- SpecIF:LocalTerm: Stakeholder Group
- SpecIF:multiple: false
- SpecIF:TextFormat: plain
- SpecIF:StringMaxLength: 32

## SpecIF:Perspective (SpecIF:TermPropertyClassString)
- dcterms:identifier: PC-Perspective
- SpecIF:Revision: 1.2
- dcterms:description: Enumerated values for the perspective (of a requirement).
- SpecIF:TermStatus: SpecIF:LifecycleStatusDeprecated
- SpecIF:LocalTerm: Perspective
- SpecIF:isRequired: false
- SpecIF:multiple: false
- SpecIF:TextFormat: plain
- SpecIF:StringMaxLength: 32

## SpecIF:Responsible (SpecIF:TermPropertyClassString)
- dcterms:description: The 'Person' being responsible for the resource.
- SpecIF:TermStatus: SpecIF:LifecycleStatusReleased
- SpecIF:LocalTerm: Responsible

## SpecIF:Accountable (SpecIF:TermPropertyClassString)
- dcterms:description: The 'Person' being accountable for the resource.
- SpecIF:TermStatus: SpecIF:LifecycleStatusReleased
- SpecIF:LocalTerm: Accountable
- SpecIF:multiple: false

## SpecIF:Milestone (SpecIF:TermPropertyClassTimestamp)
- dcterms:description: A target 'Milestone' to implement the resource.
- SpecIF:TermStatus: SpecIF:LifecycleStatusReleased
- SpecIF:LocalTerm: Milestone

## SpecIF:DueDate (SpecIF:TermPropertyClassTimestamp)
- dcterms:description: A 'Due Date' for the resource.
- SpecIF:TermStatus: SpecIF:LifecycleStatusReleased
- SpecIF:LocalTerm: Due Date

## SpecIF:Benefit (SpecIF:TermPropertyClassString)
- SpecIF:TermStatus: SpecIF:LifecycleStatusReleased
- SpecIF:LocalTerm: Benefit
- SpecIF:multiple: false
- SpecIF:TextFormat: plain

## SpecIF:Damage (SpecIF:TermPropertyClassString)
- SpecIF:TermStatus: SpecIF:LifecycleStatusReleased
- SpecIF:LocalTerm: Damage
- SpecIF:multiple: false
- SpecIF:TextFormat: plain

## SpecIF:Icon (SpecIF:TermPropertyClassString)
- dcterms:identifier: PC-Icon
- SpecIF:Revision: 1.1
- dcterms:description: A symbol or icon for display as a prefix to titles; applicable to all instances of the class. Is usually a XML-encoded UTF-8 symbol, can be an URL or dataURL.
- SpecIF:TermStatus: SpecIF:LifecycleStatusReleased
- SpecIF:LocalTerm: Icon
- SpecIF:isRequired: false
- SpecIF:multiple: false
- SpecIF:StringMaxLength: 256

## SpecIF:Unit (SpecIF:TermPropertyClassString)
- dcterms:identifier: PC-Unit
- SpecIF:Revision: 1.2
- dcterms:description: The unit of a property's numeric value; preferably an SI unit symbol such as 'm^3/kg' (Système international (d'unités)) or a currency symbol.
- SpecIF:Domain: SpecIF:DomainSystemModelIntegration
- SpecIF:TermStatus: SpecIF:LifecycleStatusReleased
- SpecIF:LocalTerm: Unit
- SpecIF:isRequired: false
- SpecIF:multiple: false
- SpecIF:TextFormat: plain
- SpecIF:StringMaxLength: 32

## SpecIF:Tag (SpecIF:TermPropertyClassString)
- SpecIF:TermStatus: SpecIF:LifecycleStatusReleased
- SpecIF:LocalTerm: Tag
- SpecIF:multiple: true
- SpecIF:TextFormat: plain
- SpecIF:StringMaxLength: 32

## SpecIF:Instantiation (SpecIF:TermPropertyClassString)
- dcterms:identifier: PC-Instantiation
- SpecIF:Revision: 1.1
- dcterms:description: Indicates whether an instance of the class is created automatically, manually or both. Manual *and* automatic instantiation is allowed, if the property is omitted. The class is abstract and cannot be instantiated, if the property list is present, but empty.
  -'user': a user creates, updates and deletes a resource's instance manually.
  -'auto': a resource's instance is created, updated or deleted by an algorithm.
- SpecIF:TermStatus: SpecIF:LifecycleStatusReleased
- SpecIF:LocalTerm: Instantiation
- SpecIF:isRequired: false
- SpecIF:multiple: true
- SpecIF:TextFormat: plain
- SpecIF:StringMaxLength: 32

## SpecIF:Creation (SpecIF:TermPropertyClassString)
- dcterms:description: 'manual': user interface supports creation, update and deletion of the resource.
  'auto': the resource is created, updated or deleted by an algorithm.
- SpecIF:TermStatus: SpecIF:LifecycleStatusDeprecated
- SpecIF:multiple: false

## SpecIF:Origin (SpecIF:TermPropertyClassString)
- dcterms:description: The origin (source, reference) of an information or requirement
- SpecIF:Revision: 1.2
- SpecIF:TermStatus: SpecIF:LifecycleStatusReleased
- SpecIF:LocalTerm: Origin, Initiator
- SpecIF:TextFormat: xhtml
- SpecIF:multiple: true
- SpecIF:StringMaxLength: 256

## SpecIF:hasSubject (SpecIF:TermPropertyClassString)
- SpecIF:Revision: 1.2
- dcterms:description: The subject of a subject-predicate-object statement. Corresponds to a 'source' in ReqIF terminology.
- SpecIF:TermStatus: SpecIF:LifecycleStatusReleased
- SpecIF:LocalTerm: Subject
- SpecIF:isRequired: false
- SpecIF:multiple: false
- SpecIF:StringMaxLength: 256

## SpecIF:Source (SpecIF:TermPropertyClassString)
- dcterms:description: The subject of a subject-predicate-object statement.
- SpecIF:TermStatus: SpecIF:LifecycleStatusDeprecated
- SpecIF:LocalTerm: Source
- SpecIF:StringMaxLength: 256

## SpecIF:Subject (SpecIF:TermPropertyClassString)
- dcterms:description: The subject of a subject-predicate-object statement.
- SpecIF:TermStatus: SpecIF:LifecycleStatusDeprecated
- SpecIF:LocalTerm: Source
- SpecIF:isRequired: false
- SpecIF:multiple: false
- SpecIF:StringMaxLength: 256

## SpecIF:hasObject (SpecIF:TermPropertyClassString)
- SpecIF:Revision: 1.2
- dcterms:description: The object of a subject-predicate-object statement. Corresponds to a 'target' in ReqIF terminology.
- SpecIF:TermStatus: SpecIF:LifecycleStatusReleased
- SpecIF:LocalTerm: Object
- SpecIF:isRequired: false
- SpecIF:multiple: false
- SpecIF:StringMaxLength: 256

## SpecIF:Target (SpecIF:TermPropertyClassString)
- dcterms:description: The object of a subject-predicate-object statement.
- SpecIF:TermStatus: SpecIF:LifecycleStatusDeprecated
- SpecIF:LocalTerm: Target
- SpecIF:StringMaxLength: 256

## SpecIF:Object (SpecIF:TermPropertyClassString)
- dcterms:description: The object of a subject-predicate-object statement.
- SpecIF:TermStatus: SpecIF:LifecycleStatusDeprecated
- SpecIF:LocalTerm: Target
- SpecIF:isRequired: false
- SpecIF:multiple: false
- SpecIF:StringMaxLength: 256

## SpecIF:FitCriteria (SpecIF:TermPropertyClassString)
- SpecIF:TermStatus: SpecIF:LifecycleStatusReleased
- SpecIF:LocalTerm: Fit Criteria

## SpecIF:OrdinalMark (SpecIF:TermPropertyClassString)
- dcterms:description: A string to determine the ordering of elements. Rules:
  - For ordering, only alphanumeric characters are permissible. Uppercase or lowerCase has no effect; thus, 'F' is equivalent to 'f'.
  - The ordering at character level is alphanumeric, i.e. '1' < '7' < 'D' < 'X'.
  - Single character substrings < two-character substrings < substrings with more characters, thus '9' < '12' < '114'.
  - The ordinal mark may be separated by non-alphanumeric characters. All separators are equivalent; e.g. '-' is equivalent to ';' or '/'.
  - Each alphanumeric substring is used for ordering on its hierarchical level; the leftmost substring is most significant for the overall ordering.
  - For example '1' < '1.2' < '1.Y' < '1.1a' < '1-1b' < '1-1C' < '2'.
  A regular expression for extracting the substrings of an ordinal mark is /([0-9a-z]+)[^0-9a-z]{0,1}/gi.
- SpecIF:TermStatus: SpecIF:LifecycleStatusExperimental
- SpecIF:LocalTerm: Ordinal Mark

## SpecIF:multiple (SpecIF:TermPropertyClassBoolean)
- dcterms:identifier: PC-multiple
- SpecIF:Revision: 1.1
- dcterms:description: The property may have multiple values; by default, it is 'false'.
- SpecIF:Domain: SpecIF:DomainOntology
- SpecIF:TermStatus: SpecIF:LifecycleStatusReleased
- SpecIF:LocalTerm: multiple values
- SpecIF:isRequired: false
- SpecIF:multiple: false
- SpecIF:DefaultValueBoolean: false

## SpecIF:singleLanguage (SpecIF:TermPropertyClassBoolean)
- dcterms:identifier: PC-singleLanguage
- SpecIF:Revision: 1.2
- dcterms:description: A property value must not have more than a single languages; by default, it is 'false'.
- SpecIF:Domain: SpecIF:DomainOntology
- SpecIF:TermStatus: SpecIF:LifecycleStatusReleased
- SpecIF:LocalTerm: single-language
- SpecIF:multiple: false
- SpecIF:DefaultValueBoolean: false

## SpecIF:isHeading (SpecIF:TermPropertyClassBoolean)
- dcterms:identifier: PC-isHeading
- SpecIF:Revision: 1.1
- dcterms:description: Indicates whether the resource is a heading, e.g. for adding automatic numbering or influencing the display size.
- SpecIF:Domain: SpecIF:DomainOntology
- SpecIF:TermStatus: SpecIF:LifecycleStatusReleased
- SpecIF:LocalTerm: Heading
- SpecIF:isRequired: false
- SpecIF:multiple: false
- SpecIF:DefaultValueBoolean: false

## SpecIF:isUndirected (SpecIF:TermPropertyClassBoolean)
- dcterms:identifier: PC-isUndirected
- SpecIF:Revision: 1.1
- dcterms:description: Indicates whether the statement is undirected, i.e. whether is can be reversed without change in meaning. A typical example is [[SpecIF:isSynonymOf]].
- SpecIF:Domain: SpecIF:DomainOntology
- SpecIF:TermStatus: SpecIF:LifecycleStatusReleased
- SpecIF:LocalTerm: undirected
- SpecIF:isRequired: false
- SpecIF:multiple: false
- SpecIF:DefaultValueBoolean: false

## SpecIF:isRequired (SpecIF:TermPropertyClassBoolean)
- dcterms:identifier: PC-isRequired
- SpecIF:Revision: 1.1
- dcterms:description: Indicates whether the property is required.
- SpecIF:Domain: SpecIF:DomainOntology
- SpecIF:TermStatus: SpecIF:LifecycleStatusReleased
- SpecIF:LocalTerm: required, mandatory
- SpecIF:isRequired: false
- SpecIF:multiple: false
- SpecIF:DefaultValueBoolean: false

## SpecIF:DefaultValue (SpecIF:TermPropertyClassString)
- dcterms:identifier: PC-DefaultValue
- SpecIF:Revision: 1.1
- SpecIF:TermStatus: SpecIF:LifecycleStatusReleased
- SpecIF:LocalTerm: Default Value
- SpecIF:multiple: false
- SpecIF:TextFormat: plain

## SpecIF:DefaultValueString (SpecIF:TermPropertyClassString)
- dcterms:identifier: PC-DefaultValueString
- SpecIF:Revision: 1.1
- dcterms:description: Default values for a property of type 'string' with multiple languages.
- SpecIF:Domain: SpecIF:DomainOntology
- SpecIF:TermStatus: SpecIF:LifecycleStatusReleased
- SpecIF:LocalTerm: Default Value
- SpecIF:isRequired: false
- SpecIF:multiple: false
- SpecIF:TextFormat: xhtml

## SpecIF:DefaultValueBoolean (SpecIF:TermPropertyClassBoolean)
- dcterms:identifier: PC-DefaultValueBoolean
- SpecIF:Revision: 1.1
- dcterms:description: Default values for a property of type 'boolean'.
- SpecIF:Domain: SpecIF:DomainOntology
- SpecIF:TermStatus: SpecIF:LifecycleStatusReleased
- SpecIF:LocalTerm: Default Value
- SpecIF:isRequired: false
- SpecIF:multiple: false
- SpecIF:DefaultValueBoolean: false

## SpecIF:DefaultValueInteger (SpecIF:TermPropertyClassInteger)
- dcterms:identifier: PC-DefaultValueInteger
- SpecIF:Revision: 1.1
- dcterms:description: Default values for a property of type 'integer'.
- SpecIF:Domain: SpecIF:DomainOntology
- SpecIF:TermStatus: SpecIF:LifecycleStatusReleased
- SpecIF:LocalTerm: Default Value
- SpecIF:isRequired: false
- SpecIF:multiple: false

## SpecIF:DefaultValueReal (SpecIF:TermPropertyClassReal)
- dcterms:identifier: PC-DefaultValueReal
- SpecIF:Revision: 1.1
- dcterms:description: Default values for a property of type 'real'.
- SpecIF:Domain: SpecIF:DomainOntology
- SpecIF:TermStatus: SpecIF:LifecycleStatusReleased
- SpecIF:LocalTerm: Default Value
- SpecIF:isRequired: false
- SpecIF:multiple: false

## SpecIF:DefaultValueTimestamp (SpecIF:TermPropertyClassTimestamp)
- dcterms:identifier: PC-DefaultValueTimestamp
- SpecIF:Revision: 1.1
- dcterms:description: Default values for a property of type 'dateTime'.
- SpecIF:Domain: SpecIF:DomainOntology
- SpecIF:TermStatus: SpecIF:LifecycleStatusReleased
- SpecIF:LocalTerm: Default Value
- SpecIF:isRequired: false
- SpecIF:multiple: false

## SpecIF:DefaultValueDuration (SpecIF:TermPropertyClassDuration)
- dcterms:identifier: PC-DefaultValueDuration
- SpecIF:Revision: 1.1
- dcterms:description: Default values for a property of type 'duration'.
- SpecIF:Domain: SpecIF:DomainOntology
- SpecIF:TermStatus: SpecIF:LifecycleStatusReleased
- SpecIF:LocalTerm: Default Value
- SpecIF:isRequired: false
- SpecIF:multiple: false

## SpecIF:DefaultValueAnyURI (SpecIF:TermPropertyClassURI)
- dcterms:identifier: PC-DefaultValueAnyURI
- SpecIF:Revision: 1.1
- dcterms:description: Default values for a property of type 'anyURI'.
- SpecIF:TermStatus: SpecIF:LifecycleStatusEquivalent
- SpecIF:LocalTerm: Default Value
- SpecIF:isRequired: false
- SpecIF:multiple: false

## SpecIF:TextFormat (SpecIF:TermPropertyClassString)
- dcterms:identifier: PC-TextFormat
- SpecIF:Revision: 1.1
- dcterms:description: The type of formatting, plain or XHTML.
- SpecIF:Domain: SpecIF:DomainOntology
- SpecIF:TermStatus: SpecIF:LifecycleStatusReleased
- SpecIF:LocalTerm: Text format
- SpecIF:isRequired: false
- SpecIF:multiple: false
- SpecIF:TextFormat: plain
- SpecIF:StringMaxLength: 32

## SpecIF:StringMaxLength (SpecIF:TermPropertyClassInteger)
- dcterms:identifier: PC-StringMaxLength
- SpecIF:Revision: 1.1
- dcterms:description: Maximum length of a string value.
- SpecIF:Domain: SpecIF:DomainOntology
- SpecIF:TermStatus: SpecIF:LifecycleStatusReleased
- SpecIF:LocalTerm: max. Length
- SpecIF:isRequired: false
- SpecIF:multiple: false
- SpecIF:IntegerMinInclusive: 0
- SpecIF:IntegerMaxInclusive: 2147483647

## SpecIF:IntegerMinInclusive (SpecIF:TermPropertyClassInteger)
- dcterms:identifier: PC-IntegerMinInclusive
- SpecIF:Revision: 1.1
- dcterms:description: Inclusive minimum of an integer value.
- SpecIF:Domain: SpecIF:DomainOntology
- SpecIF:TermStatus: SpecIF:LifecycleStatusReleased
- SpecIF:LocalTerm: min. Value
- SpecIF:isRequired: false
- SpecIF:multiple: false
- SpecIF:IntegerMinInclusive: -2147483648
- SpecIF:IntegerMaxInclusive: 2147483647

## SpecIF:IntegerMaxInclusive (SpecIF:TermPropertyClassInteger)
- dcterms:identifier: PC-IntegerMaxInclusive
- SpecIF:Revision: 1.1
- dcterms:description: Inclusive maximum of an integer value.
- SpecIF:Domain: SpecIF:DomainOntology
- SpecIF:TermStatus: SpecIF:LifecycleStatusReleased
- SpecIF:LocalTerm: max. Value
- SpecIF:isRequired: false
- SpecIF:multiple: false
- SpecIF:IntegerMinInclusive: -2147483648
- SpecIF:IntegerMaxInclusive: 2147483647

## SpecIF:RealMinInclusive (SpecIF:TermPropertyClassReal)
- dcterms:identifier: PC-RealMinInclusive
- SpecIF:Revision: 1.1
- dcterms:description: Inclusive minimum of a real value.
- SpecIF:Domain: SpecIF:DomainOntology
- SpecIF:LocalTerm: min. Value
- SpecIF:isRequired: false
- SpecIF:multiple: false

## SpecIF:RealMaxInclusive (SpecIF:TermPropertyClassReal)
- dcterms:identifier: PC-RealMaxInclusive
- SpecIF:Revision: 1.1
- dcterms:description: Inclusive maximum of a real value.
- SpecIF:Domain: SpecIF:DomainOntology
- SpecIF:LocalTerm: max. Value
- SpecIF:isRequired: false
- SpecIF:multiple: false

## SpecIF:RealFractionDigits (SpecIF:TermPropertyClassInteger)
- dcterms:identifier: PC-RealFractionDigits
- SpecIF:Revision: 1.1
- dcterms:description: Max. count of decimals of a real number.
- SpecIF:Domain: SpecIF:DomainOntology
- SpecIF:LocalTerm: Decimals
- SpecIF:isRequired: false
- SpecIF:multiple: false
- SpecIF:DefaultValueInteger: 2
- SpecIF:IntegerMinInclusive: 0
- SpecIF:IntegerMaxInclusive: 2147483647

## ReqIF-WF.CustomerStatus (SpecIF:TermPropertyClassString)
- dcterms:identifier: PC-CustomerStatus
- SpecIF:Revision: 1.2
- SpecIF:Domain: SpecIF:DomainRequirementsEngineeringSRC
- SpecIF:TermStatus: SpecIF:LifecycleStatusReleased
- SpecIF:LocalTerm: Customer Status
- SpecIF:multiple: false
- SpecIF:TextFormat: plain
- SpecIF:StringMaxLength: 32

## ReqIF-WF.CustomerComment (SpecIF:TermPropertyClassString)
- dcterms:identifier: PC-CustomerComment
- SpecIF:Revision: 1.2
- SpecIF:Domain: SpecIF:DomainRequirementsEngineeringSRC
- SpecIF:TermStatus: SpecIF:LifecycleStatusReleased
- SpecIF:LocalTerm: Customer Comment
- SpecIF:multiple: true
- SpecIF:TextFormat: xhtml

## ReqIF-WF.SupplierStatus (SpecIF:TermPropertyClassString)
- dcterms:identifier: PC-SupplierStatus
- SpecIF:Revision: 1.2
- SpecIF:Domain: SpecIF:DomainRequirementsEngineeringSRC
- SpecIF:TermStatus: SpecIF:LifecycleStatusReleased
- SpecIF:LocalTerm: Supplier Status
- SpecIF:multiple: false
- SpecIF:TextFormat: plain
- SpecIF:StringMaxLength: 32

## ReqIF-WF.SupplierComment (SpecIF:TermPropertyClassString)
- dcterms:identifier: PC-SupplierComment
- SpecIF:Revision: 1.2
- SpecIF:Domain: SpecIF:DomainRequirementsEngineeringSRC
- SpecIF:TermStatus: SpecIF:LifecycleStatusReleased
- SpecIF:LocalTerm: Supplier Comment
- SpecIF:multiple: true
- SpecIF:TextFormat: xhtml

## HIS:OemStatus (SpecIF:TermPropertyClassString)
- SpecIF:Domain: SpecIF:DomainRequirementsEngineeringSRC
- SpecIF:TermStatus: SpecIF:LifecycleStatusEquivalent

## HIS:OemComment (SpecIF:TermPropertyClassString)
- SpecIF:Domain: SpecIF:DomainRequirementsEngineeringSRC
- SpecIF:TermStatus: SpecIF:LifecycleStatusEquivalent

## HIS:SupplierStatus (SpecIF:TermPropertyClassString)
- SpecIF:Domain: SpecIF:DomainRequirementsEngineeringSRC
- SpecIF:TermStatus: SpecIF:LifecycleStatusEquivalent

## HIS:SupplierComment (SpecIF:TermPropertyClassString)
- SpecIF:Domain: SpecIF:DomainRequirementsEngineeringSRC
- SpecIF:TermStatus: SpecIF:LifecycleStatusEquivalent

## xs:string (SpecIF:TermPropertyClassString)
- SpecIF:Revision: 1.2
- dcterms:description: The string datatype represents character strings in XML. The ·value space· of string is the set of finite-length sequences of [characters](http://www.w3.org/TR/2000/WD-xml-2e-20000814#dt-character) (as defined in [XML 1.0 (Second Edition)](https://www.w3.org/TR/xmlschema-2/#XML)) that ·match· the [Char](http://www.w3.org/TR/2000/WD-xml-2e-20000814#NT-Char) production from [XML 1.0 (Second Edition)](https://www.w3.org/TR/xmlschema-2/#XML). A [character](http://www.w3.org/TR/2000/WD-xml-2e-20000814#dt-character) is an atomic unit of communication; it is not further specified except to note that every [character](http://www.w3.org/TR/2000/WD-xml-2e-20000814#dt-character) has a corresponding Universal Character Set code point, which is an integer.
- SpecIF:Domain: SpecIF:DomainBase
- SpecIF:TermStatus: SpecIF:LifecycleStatusReleased
- SpecIF:LocalTerm: String

## xs:boolean (SpecIF:TermPropertyClassBoolean)
- dcterms:identifier: PC-Boolean
- SpecIF:Revision: 1.2
- dcterms:description: The Boolean data type.
- SpecIF:Domain: SpecIF:DomainBase
- SpecIF:TermStatus: SpecIF:LifecycleStatusReleased
- SpecIF:LocalTerm: Boolean

## xs:integer (SpecIF:TermPropertyClassInteger)
- dcterms:identifier: PC-Integer
- SpecIF:Revision: 1.2
- dcterms:description: A numerical integer value from -2147483648 to 2147483647 (32 bit).
- SpecIF:Domain: SpecIF:DomainBase
- SpecIF:TermStatus: SpecIF:LifecycleStatusReleased
- SpecIF:LocalTerm: Integer
- SpecIF:IntegerMinInclusive: -2147483648
- SpecIF:IntegerMaxInclusive: 2147483647

## xs:unsignedByte (SpecIF:TermPropertyClassInteger)
- dcterms:identifier: PC-Byte
- SpecIF:Revision: 1.2
- dcterms:description: An unsigned byte is an integer value between 0 and 255.
- SpecIF:Domain: SpecIF:DomainBase
- SpecIF:TermStatus: SpecIF:LifecycleStatusReleased
- SpecIF:LocalTerm: Integer
- SpecIF:IntegerMinInclusive: 0
- SpecIF:IntegerMaxInclusive: 255

## xs:double (SpecIF:TermPropertyClassReal)
- dcterms:identifier: PC-Real
- SpecIF:Revision: 1.2
- dcterms:description: A floating point number (double).
- SpecIF:Domain: SpecIF:DomainBase
- SpecIF:TermStatus: SpecIF:LifecycleStatusReleased
- SpecIF:LocalTerm: Real

## xs:dateTime (SpecIF:TermPropertyClassTimestamp)
- dcterms:identifier: PC-DateTime
- SpecIF:Revision: 1.2
- dcterms:description: Date or timestamp in ISO-8601 format.
- SpecIF:Domain: SpecIF:DomainBase
- SpecIF:TermStatus: SpecIF:LifecycleStatusReleased
- SpecIF:LocalTerm: Date or Timestamp

## xs:duration (SpecIF:TermPropertyClassDuration)
- dcterms:identifier: PC-Duration
- SpecIF:Revision: 1.2
- dcterms:description: A duration as defined by the ISO 8601 ABNF for 'duration'.
- SpecIF:Domain: SpecIF:DomainBase
- SpecIF:TermStatus: SpecIF:LifecycleStatusReleased
- SpecIF:LocalTerm: Duration

## xs:anyURI (SpecIF:TermPropertyClassURI)
- dcterms:identifier: PC-AnyURI
- SpecIF:Revision: 1.2
- dcterms:description: A universal resource identifier (URI), according to RFC3986.
- SpecIF:Domain: SpecIF:DomainBase
- SpecIF:TermStatus: SpecIF:LifecycleStatusReleased
- SpecIF:LocalTerm: Any URI

## oslc_cm:Status (SpecIF:TermPropertyClassString)
- SpecIF:Revision: 1.2
- dcterms:description: Used to indicate the status of the change request based on values defined by the service provider. Most often a read-only property. It is likely that the target resource will be a string corresponding to an oslc_cm:State value.
- SpecIF:Domain: SpecIF:DomainAgileSystemDevelopment, SpecIF:DomainSystemTesting, SpecIF:DomainProductLifecycleManagement
- SpecIF:TermStatus: SpecIF:LifecycleStatusSubmitted
- SpecIF:LocalTerm: Status
- SpecIF:isRequired: false
- SpecIF:multiple: false
- SpecIF:TextFormat: plain
- SpecIF:StringMaxLength: 32

## oslc_cm:Priority (SpecIF:TermPropertyClassString)
- SpecIF:Revision: 1.2
- dcterms:description: Used to indicate the relative importance of ChangeRequests. It is likely that the target resource will be an oslc_cm:Priority.
- SpecIF:Domain: SpecIF:DomainAgileSystemDevelopment, SpecIF:DomainSystemTesting, SpecIF:DomainProductLifecycleManagement
- SpecIF:TermStatus: SpecIF:LifecycleStatusSubmitted
- SpecIF:LocalTerm: Priority
- SpecIF:isRequired: false
- SpecIF:multiple: false
- SpecIF:TextFormat: plain
- SpecIF:StringMaxLength: 32

## oslc_cm:Severity (SpecIF:TermPropertyClassString)
- SpecIF:Revision: 1.2
- dcterms:description: Used to indicate the severity or potential impact of a defect. It is likely that the target resource will be an oslc_cm:Severity.
- SpecIF:Domain: SpecIF:DomainAgileSystemDevelopment, SpecIF:DomainSystemTesting, SpecIF:DomainProductLifecycleManagement
- SpecIF:TermStatus: SpecIF:LifecycleStatusSubmitted
- SpecIF:LocalTerm: Severity
- SpecIF:isRequired: false
- SpecIF:multiple: false
- SpecIF:TextFormat: plain
- SpecIF:StringMaxLength: 32

## Property Value Terms (SpecIF:Heading)
- dcterms:description: These are terms for certain enumerated property values. Not only the property titles, but also any enumerated value must be mapped between different systems or domains; therefore using defined terms is beneficial. Of course, like any other vocabulary term, a term used as property value for transmission or storage can be translated for display.

## FMC:Entity-Relationship_Diagram (SpecIF:TermPropertyValue)
- SpecIF:Revision: 1.2
- dcterms:description: One of tree diagram types defined by the Fundamental Modeling Concepts (FMC). See the [FMC Notation Reference](http://www.fmc-modeling.org/notation_reference).
- SpecIF:Domain: SpecIF:DomainSystemsEngineering, SpecIF:DomainSystemModelIntegration
- SpecIF:TermStatus: SpecIF:LifecycleStatusReleased
- SpecIF:LocalTerm: FMC Entity Relation Diagram

## FMC:Petri_Net (SpecIF:TermPropertyValue)
- SpecIF:Revision: 1.2
- dcterms:description: One of tree diagram types defined by the Fundamental Modeling Concepts (FMC). See the [FMC Notation Reference](http://www.fmc-modeling.org/notation_reference).
- SpecIF:Domain: SpecIF:DomainSystemsEngineering, SpecIF:DomainSystemModelIntegration
- SpecIF:TermStatus: SpecIF:LifecycleStatusReleased
- SpecIF:LocalTerm: FMC Petri Net

## FMC:Block_Diagram (SpecIF:TermPropertyValue)
- SpecIF:Revision: 1.2
- dcterms:description: One of tree diagram types defined by the Fundamental Modeling Concepts (FMC). See the [FMC Notation Reference](http://www.fmc-modeling.org/notation_reference).
- SpecIF:Domain: SpecIF:DomainSystemsEngineering, SpecIF:DomainSystemModelIntegration
- SpecIF:TermStatus: SpecIF:LifecycleStatusReleased
- SpecIF:LocalTerm: FMC Block Diagram

## uml:Class_Diagram (SpecIF:TermPropertyValue)
- SpecIF:Revision: 1.2
- SpecIF:Domain: SpecIF:DomainSystemsEngineering, SpecIF:DomainSystemModelIntegration
- SpecIF:TermStatus: SpecIF:LifecycleStatusReleased
- SpecIF:LocalTerm: UML Class Diagram

## uml:Activity_Diagram (SpecIF:TermPropertyValue)
- SpecIF:Revision: 1.2
- SpecIF:Domain: SpecIF:DomainSystemsEngineering, SpecIF:DomainSystemModelIntegration
- SpecIF:TermStatus: SpecIF:LifecycleStatusReleased
- SpecIF:LocalTerm: UML Activity Diagram

## SpecIF:priorityHigh (SpecIF:TermPropertyValue)
- dcterms:description: A value for property [[SpecIF:Priority]].
- SpecIF:LocalTerm: high, 1_high
- SpecIF:Domain: SpecIF:DomainRequirementsEngineering, SpecIF:DomainRequirementsEngineeringSRC, SpecIF:DomainSystemModelIntegration
- SpecIF:TermStatus: SpecIF:LifecycleStatusReleased

## SpecIF:priorityRatherHigh (SpecIF:TermPropertyValue)
- dcterms:description: A value for property [[SpecIF:Priority]].
- SpecIF:LocalTerm: rather high
- SpecIF:Domain: SpecIF:DomainRequirementsEngineering, SpecIF:DomainRequirementsEngineeringSRC, SpecIF:DomainSystemModelIntegration
- SpecIF:TermStatus: SpecIF:LifecycleStatusReleased

## SpecIF:priorityMedium (SpecIF:TermPropertyValue)
- dcterms:description: A value for property [[SpecIF:Priority]].
- SpecIF:LocalTerm: medium, 2_medium
- SpecIF:Domain: SpecIF:DomainRequirementsEngineering, SpecIF:DomainRequirementsEngineeringSRC, SpecIF:DomainSystemModelIntegration
- SpecIF:TermStatus: SpecIF:LifecycleStatusReleased

## SpecIF:priorityRatherLow (SpecIF:TermPropertyValue)
- dcterms:description: A value for property [[SpecIF:Priority]].
- SpecIF:LocalTerm: rather low
- SpecIF:Domain: SpecIF:DomainRequirementsEngineering, SpecIF:DomainRequirementsEngineeringSRC, SpecIF:DomainSystemModelIntegration
- SpecIF:TermStatus: SpecIF:LifecycleStatusReleased

## SpecIF:priorityLow (SpecIF:TermPropertyValue)
- dcterms:description: A value for property [[SpecIF:Priority]].
- SpecIF:LocalTerm: low, 3_low
- SpecIF:Domain: SpecIF:DomainRequirementsEngineering, SpecIF:DomainRequirementsEngineeringSRC, SpecIF:DomainSystemModelIntegration
- SpecIF:TermStatus: SpecIF:LifecycleStatusReleased

## SpecIF:sizeXL (SpecIF:TermPropertyValue)
- dcterms:description: T-shirt sizes have become popular to classify [[IREB:Risk]], [[SpecIF:Damage]] or similar. Translates to 'very large' in English.
- SpecIF:TermStatus: SpecIF:LifecycleStatusExperimental
- SpecIF:LocalTerm: XL, very big

## SpecIF:sizeL (SpecIF:TermPropertyValue)
- dcterms:description: T-shirt sizes have become popular to classify [[IREB:Risk]], [[SpecIF:Damage]] or similar. Translates to 'large' in English.
- SpecIF:TermStatus: SpecIF:LifecycleStatusExperimental
- SpecIF:LocalTerm: L, big

## SpecIF:sizeM (SpecIF:TermPropertyValue)
- dcterms:description: T-shirt sizes have become popular to classify [[IREB:Risk]], [[SpecIF:Damage]] or similar. Translates to 'medium' in English.
- SpecIF:TermStatus: SpecIF:LifecycleStatusExperimental
- SpecIF:LocalTerm: M, medium

## SpecIF:sizeS (SpecIF:TermPropertyValue)
- dcterms:description: T-shirt sizes have become popular to classify [[IREB:Risk]], [[SpecIF:Damage]] or similar. Translates to 'small' in English.
- SpecIF:TermStatus: SpecIF:LifecycleStatusExperimental
- SpecIF:LocalTerm: S, small

## SpecIF:sizeXS (SpecIF:TermPropertyValue)
- dcterms:description: T-shirt sizes have become popular to classify [[IREB:Risk]], [[SpecIF:Damage]] or similar. Translates to 'very small' in English.
- SpecIF:TermStatus: SpecIF:LifecycleStatusExperimental
- SpecIF:LocalTerm: XS, very small

## SpecIF:LifecycleStatusInitial (SpecIF:TermPropertyValue)
- dcterms:identifier: V-TermStatus-00
- SpecIF:Revision: 1.2
- SpecIF:TermStatus: SpecIF:LifecycleStatusSubmitted
- SpecIF:LocalTerm: initial, 10_initial

## SpecIF:LifecycleStatusDrafted (SpecIF:TermPropertyValue)
- dcterms:identifier: V-TermStatus-10
- SpecIF:Revision: 1.2
- SpecIF:TermStatus: SpecIF:LifecycleStatusSubmitted
- SpecIF:LocalTerm: drafted, bearbeitet, 20_drafted

## SpecIF:LifecycleStatusSubmitted (SpecIF:TermPropertyValue)
- SpecIF:Revision: 1.2
- SpecIF:LocalTerm: submitted, 30_submitted, 30_entscheidungsreif

## SpecIF:LifecycleStatusExperimental (SpecIF:TermPropertyValue)
- SpecIF:Revision: 1.2
- SpecIF:Domain: SpecIF:DomainOntology
- SpecIF:TermStatus: SpecIF:LifecycleStatusSubmitted
- SpecIF:LocalTerm: experimental

## SpecIF:LifecycleStatusApproved (SpecIF:TermPropertyValue)
- dcterms:identifier: V-TermStatus-20
- SpecIF:Revision: 1.2
- SpecIF:TermStatus: SpecIF:LifecycleStatusSubmitted
- SpecIF:LocalTerm: approved, 40_approved

## SpecIF:LifecycleStatusReady (SpecIF:TermPropertyValue)
- dcterms:identifier: V-TermStatus-22
- SpecIF:Revision: 1.2
- dcterms:description: Meets the requirements of the 'Definition of Ready' of the agile development method.
- SpecIF:TermStatus: SpecIF:LifecycleStatusSubmitted
- SpecIF:LocalTerm: ready, bereit

## SpecIF:LifecycleStatusDone (SpecIF:TermPropertyValue)
- dcterms:identifier: V-TermStatus-30
- SpecIF:Revision: 1.2
- dcterms:description: Meets the requirements of the 'Definition of Done' of the agile development method.
- SpecIF:TermStatus: SpecIF:LifecycleStatusSubmitted
- SpecIF:LocalTerm: done, 60_completed

## SpecIF:LifecycleStatusValidated (SpecIF:TermPropertyValue)
- dcterms:identifier: V-TermStatus-40
- SpecIF:Revision: 1.2
- SpecIF:TermStatus: SpecIF:LifecycleStatusSubmitted
- SpecIF:LocalTerm: validated, 70_validated, 70_lab-tested

## SpecIF:LifecycleStatusReleased (SpecIF:TermPropertyValue)
- SpecIF:Revision: 1.2
- SpecIF:TermStatus: SpecIF:LifecycleStatusSubmitted
- SpecIF:LocalTerm: released, published, 80_released

## SpecIF:LifecycleStatusDeprecated (SpecIF:TermPropertyValue)
- SpecIF:Revision: 1.2
- SpecIF:TermStatus: SpecIF:LifecycleStatusSubmitted
- SpecIF:LocalTerm: deprecated, 00_deprecated

## SpecIF:LifecycleStatusWithdrawn (SpecIF:TermPropertyValue)
- dcterms:identifier: V-TermStatus-94
- SpecIF:Revision: 1.2
- SpecIF:TermStatus: SpecIF:LifecycleStatusSubmitted
- SpecIF:LocalTerm: withdrawn, 90_withdrawn

## SpecIF:LifecycleStatusPostponed (SpecIF:TermPropertyValue)
- dcterms:identifier: V-TermStatus-08
- SpecIF:Revision: 1.2
- SpecIF:TermStatus: SpecIF:LifecycleStatusSubmitted
- SpecIF:LocalTerm: postponed, 00_postponed

## SpecIF:LifecycleStatusRejected (SpecIF:TermPropertyValue)
- dcterms:identifier: V-TermStatus-98
- SpecIF:Revision: 1.2
- SpecIF:TermStatus: SpecIF:LifecycleStatusSubmitted
- SpecIF:LocalTerm: rejected, 00_rejected

## SpecIF:LifecycleStatusEquivalent (SpecIF:TermPropertyValue)
- SpecIF:Revision: 1.1
- SpecIF:Domain: SpecIF:DomainOntology
- SpecIF:TermStatus: SpecIF:LifecycleStatusSubmitted
- SpecIF:LocalTerm: equivalent

## SpecIF:EngineeringDisciplineMechanics (SpecIF:TermPropertyValue)
- SpecIF:Revision: 1.2
- SpecIF:Domain: SpecIF:DomainRequirementsEngineering, SpecIF:DomainRequirementsEngineeringSRC, SpecIF:DomainSystemModelIntegration
- SpecIF:TermStatus: SpecIF:LifecycleStatusReleased
- SpecIF:LocalTerm: Mechanics

## SpecIF:EngineeringDisciplineElectronics (SpecIF:TermPropertyValue)
- SpecIF:Revision: 1.2
- SpecIF:Domain: SpecIF:DomainRequirementsEngineering, SpecIF:DomainRequirementsEngineeringSRC, SpecIF:DomainSystemModelIntegration
- SpecIF:TermStatus: SpecIF:LifecycleStatusReleased
- SpecIF:LocalTerm: Electronics

## SpecIF:EngineeringDisciplineSoftware (SpecIF:TermPropertyValue)
- SpecIF:Revision: 1.2
- SpecIF:Domain: SpecIF:DomainRequirementsEngineering, SpecIF:DomainRequirementsEngineeringSRC, SpecIF:DomainSystemModelIntegration
- SpecIF:TermStatus: SpecIF:LifecycleStatusReleased
- SpecIF:LocalTerm: Software

## SpecIF:EngineeringDisciplineSafety (SpecIF:TermPropertyValue)
- SpecIF:Revision: 1.2
- SpecIF:Domain: SpecIF:DomainRequirementsEngineering, SpecIF:DomainRequirementsEngineeringSRC, SpecIF:DomainSystemModelIntegration
- SpecIF:TermStatus: SpecIF:LifecycleStatusReleased
- SpecIF:LocalTerm: Safety

## SpecIF:EngineeringDisciplineSystem (SpecIF:TermPropertyValue)
- SpecIF:Revision: 1.2
- SpecIF:Domain: SpecIF:DomainRequirementsEngineering, SpecIF:DomainRequirementsEngineeringSRC, SpecIF:DomainSystemModelIntegration
- SpecIF:TermStatus: SpecIF:LifecycleStatusReleased
- SpecIF:LocalTerm: System Engineering

## SpecIF:StakeholderGroupRegulation (SpecIF:TermPropertyValue)
- SpecIF:Revision: 1.2
- dcterms:description: The stakeholder group 'Regulation' addressed by a requirement.
- SpecIF:Domain: SpecIF:DomainRequirementsEngineering, SpecIF:DomainRequirementsEngineeringSRC, SpecIF:DomainSystemModelIntegration
- SpecIF:TermStatus: SpecIF:LifecycleStatusReleased
- SpecIF:LocalTerm: Regulation

## SpecIF:StakeholderGroupBusiness (SpecIF:TermPropertyValue)
- SpecIF:Revision: 1.2
- dcterms:description: The stakeholder group 'Business' addressed by a requirement.
- SpecIF:Domain: SpecIF:DomainRequirementsEngineering, SpecIF:DomainRequirementsEngineeringSRC, SpecIF:DomainSystemModelIntegration
- SpecIF:TermStatus: SpecIF:LifecycleStatusReleased
- SpecIF:LocalTerm: Business

## SpecIF:StakeholderGroupUser (SpecIF:TermPropertyValue)
- SpecIF:Revision: 1.2
- dcterms:description: The stakeholder group 'User' addressed by a requirement.
- SpecIF:Domain: SpecIF:DomainRequirementsEngineering, SpecIF:DomainRequirementsEngineeringSRC, SpecIF:DomainSystemModelIntegration
- SpecIF:TermStatus: SpecIF:LifecycleStatusReleased
- SpecIF:LocalTerm: User

## SpecIF:StakeholderGroupSystem (SpecIF:TermPropertyValue)
- SpecIF:Revision: 1.2
- dcterms:description: The stakeholder group 'System' addressed by a requirement.
- SpecIF:Domain: SpecIF:DomainRequirementsEngineering, SpecIF:DomainRequirementsEngineeringSRC, SpecIF:DomainSystemModelIntegration
- SpecIF:TermStatus: SpecIF:LifecycleStatusReleased
- SpecIF:LocalTerm: System

## SpecIF:StakeholderGroupOperation (SpecIF:TermPropertyValue)
- SpecIF:Revision: 1.2
- dcterms:description: The stakeholder group 'Operation' addressed by a requirement.
- SpecIF:Domain: SpecIF:DomainRequirementsEngineering, SpecIF:DomainRequirementsEngineeringSRC, SpecIF:DomainSystemModelIntegration
- SpecIF:TermStatus: SpecIF:LifecycleStatusReleased
- SpecIF:LocalTerm: Operation

## SpecIF:DomainBase (SpecIF:TermPropertyValue)
- SpecIF:Revision: 1.2
- SpecIF:Domain: SpecIF:DomainOntology
- SpecIF:TermStatus: SpecIF:LifecycleStatusReleased
- SpecIF:LocalTerm: Base

## SpecIF:DomainRequirementsEngineering (SpecIF:TermPropertyValue)
- SpecIF:Revision: 1.2
- SpecIF:Domain: SpecIF:DomainOntology
- SpecIF:TermStatus: SpecIF:LifecycleStatusReleased
- SpecIF:LocalTerm: Requirements Engineering

## SpecIF:DomainRequirementsEngineeringSRC (SpecIF:TermPropertyValue)
- SpecIF:Revision: 1.2
- dcterms:description: Requirements Engineering with Automotive Stakeholder Request Clarification Process (SRC) as defined by Prostep iViP e.V..
- SpecIF:Domain: SpecIF:DomainOntology
- SpecIF:TermStatus: SpecIF:LifecycleStatusReleased
- SpecIF:LocalTerm: Requirements Engineering (SRC)

## SpecIF:DomainSystemsEngineering (SpecIF:TermPropertyValue)
- SpecIF:Revision: 1.2
- SpecIF:Domain: SpecIF:DomainOntology
- SpecIF:TermStatus: SpecIF:LifecycleStatusReleased
- SpecIF:LocalTerm: Systems Engineering

## SpecIF:DomainSystemModelIntegration (SpecIF:TermPropertyValue)
- SpecIF:Revision: 1.2
- SpecIF:Domain: SpecIF:DomainOntology
- SpecIF:TermStatus: SpecIF:LifecycleStatusReleased
- SpecIF:LocalTerm: System Model Integration

## SpecIF:DomainVariantManagement (SpecIF:TermPropertyValue)
- SpecIF:Revision: 1.2
- SpecIF:Domain: SpecIF:DomainOntology
- SpecIF:TermStatus: SpecIF:LifecycleStatusReleased
- SpecIF:LocalTerm: Variant Management

## SpecIF:DomainAgileSystemDevelopment (SpecIF:TermPropertyValue)
- SpecIF:Revision: 1.2
- SpecIF:Domain: SpecIF:DomainOntology
- SpecIF:TermStatus: SpecIF:LifecycleStatusReleased
- SpecIF:LocalTerm: Agile System Development

## SpecIF:DomainIssueManagement (SpecIF:TermPropertyValue)
- SpecIF:Revision: 1.2
- SpecIF:Domain: SpecIF:DomainOntology
- SpecIF:TermStatus: SpecIF:LifecycleStatusReleased
- SpecIF:LocalTerm: Issue Management

## SpecIF:DomainSystemTesting (SpecIF:TermPropertyValue)
- SpecIF:Revision: 1.2
- SpecIF:Domain: SpecIF:DomainOntology
- SpecIF:TermStatus: SpecIF:LifecycleStatusReleased
- SpecIF:LocalTerm: System Testing

## SpecIF:DomainProductLifecycleManagement (SpecIF:TermPropertyValue)
- SpecIF:Revision: 1.2
- SpecIF:Domain: SpecIF:DomainOntology
- SpecIF:TermStatus: SpecIF:LifecycleStatusReleased
- SpecIF:LocalTerm: Product Lifecycle Management

## SpecIF:DomainOntology (SpecIF:TermPropertyValue)
- SpecIF:Revision: 1.2
- SpecIF:TermStatus: SpecIF:LifecycleStatusReleased
- SpecIF:LocalTerm: Ontology

## SpecIF:DomainOther (SpecIF:TermPropertyValue)
- SpecIF:Revision: 1.2
- SpecIF:Domain: SpecIF:DomainOntology
- SpecIF:TermStatus: SpecIF:LifecycleStatusReleased
- SpecIF:LocalTerm: Other

## IREB:RequirementTypeFunction (SpecIF:TermPropertyValue)
- dcterms:description: A requirement concerning a result of behavior that shall be provided by a function of a system (or of a component or service).
- SpecIF:TermStatus: SpecIF:LifecycleStatusEquivalent
- SpecIF:LocalTerm: Function

## IREB:RequirementTypeQuality (SpecIF:TermPropertyValue)
- dcterms:description: A [[IREB:Requirement]] that pertains to a quality concern that is not covered by functional requirements.
- SpecIF:TermStatus: SpecIF:LifecycleStatusEquivalent
- SpecIF:LocalTerm: Quality

## IREB:RequirementTypeConstraint (SpecIF:TermPropertyValue)
- dcterms:description: A [[IREB:Requirement]] that limits the solution space beyond what is necessary for meeting the given functional requirements and quality requirements.
- SpecIF:TermStatus: SpecIF:LifecycleStatusEquivalent
- SpecIF:LocalTerm: Constraint

## IREB:FunctionalRequirement (SpecIF:TermPropertyValue)
- SpecIF:Revision: 1.2
- dcterms:description: A [[IREB:Requirement]] concerning a result of behavior that shall be provided by a function of a system (or of a component or service).
- SpecIF:Domain: SpecIF:DomainRequirementsEngineering, SpecIF:DomainRequirementsEngineeringSRC
- SpecIF:TermStatus: SpecIF:LifecycleStatusReleased
- SpecIF:LocalTerm: Functional Requirement

## IREB:QualityRequirement (SpecIF:TermPropertyValue)
- SpecIF:Revision: 1.2
- dcterms:description: A [[IREB:Requirement]] that pertains to a quality concern that is not covered by functional requirements.
- SpecIF:Domain: SpecIF:DomainRequirementsEngineering, SpecIF:DomainRequirementsEngineeringSRC
- SpecIF:TermStatus: SpecIF:LifecycleStatusReleased
- SpecIF:LocalTerm: Quality Requirement

## IREB:Constraint (SpecIF:TermPropertyValue)
- SpecIF:Revision: 1.2
- dcterms:description: A [[IREB:Requirement]] that limits the solution space beyond what is necessary for meeting the given functional requirements and quality requirements.
- SpecIF:Domain: SpecIF:DomainRequirementsEngineering, SpecIF:DomainRequirementsEngineeringSRC
- SpecIF:TermStatus: SpecIF:LifecycleStatusReleased
- SpecIF:LocalTerm: Constraint

## SpecIF:PerspectiveBusiness (SpecIF:TermPropertyValue)
- SpecIF:Revision: 1.2
- SpecIF:Domain: SpecIF:DomainRequirementsEngineering, SpecIF:DomainRequirementsEngineeringSRC
- SpecIF:TermStatus: SpecIF:LifecycleStatusDeprecated
- SpecIF:LocalTerm: Business

## SpecIF:PerspectiveStakeholder (SpecIF:TermPropertyValue)
- SpecIF:Revision: 1.2
- SpecIF:Domain: SpecIF:DomainRequirementsEngineering, SpecIF:DomainRequirementsEngineeringSRC
- SpecIF:TermStatus: SpecIF:LifecycleStatusDeprecated
- SpecIF:LocalTerm: Stakeholder

## SpecIF:PerspectiveUser (SpecIF:TermPropertyValue)
- SpecIF:Revision: 1.2
- SpecIF:Domain: SpecIF:DomainRequirementsEngineering, SpecIF:DomainRequirementsEngineeringSRC
- SpecIF:TermStatus: SpecIF:LifecycleStatusDeprecated
- SpecIF:LocalTerm: User

## SpecIF:PerspectiveOperator (SpecIF:TermPropertyValue)
- SpecIF:Revision: 1.2
- SpecIF:Domain: SpecIF:DomainRequirementsEngineering, SpecIF:DomainRequirementsEngineeringSRC
- SpecIF:TermStatus: SpecIF:LifecycleStatusDeprecated
- SpecIF:LocalTerm: Operator

## SpecIF:PerspectiveSystem (SpecIF:TermPropertyValue)
- SpecIF:Revision: 1.2
- SpecIF:Domain: SpecIF:DomainRequirementsEngineering, SpecIF:DomainRequirementsEngineeringSRC
- SpecIF:TermStatus: SpecIF:LifecycleStatusDeprecated
- SpecIF:LocalTerm: System

## SpecIF:DisciplineSystem (SpecIF:TermPropertyValue)
- SpecIF:Domain: SpecIF:DomainRequirementsEngineering, SpecIF:DomainRequirementsEngineeringSRC
- SpecIF:TermStatus: SpecIF:LifecycleStatusDeprecated
- SpecIF:LocalTerm: System

## SpecIF:DisciplineSystemEngineering (SpecIF:TermPropertyValue)
- SpecIF:Domain: SpecIF:DomainRequirementsEngineering, SpecIF:DomainRequirementsEngineeringSRC
- SpecIF:TermStatus: SpecIF:LifecycleStatusDeprecated
- SpecIF:LocalTerm: System

## SpecIF:DisciplineMechanics (SpecIF:TermPropertyValue)
- SpecIF:Domain: SpecIF:DomainRequirementsEngineering, SpecIF:DomainRequirementsEngineeringSRC
- SpecIF:TermStatus: SpecIF:LifecycleStatusDeprecated
- SpecIF:LocalTerm: Mechanics

## SpecIF:DisciplineElectronics (SpecIF:TermPropertyValue)
- SpecIF:Domain: SpecIF:DomainRequirementsEngineering, SpecIF:DomainRequirementsEngineeringSRC
- SpecIF:TermStatus: SpecIF:LifecycleStatusDeprecated
- SpecIF:LocalTerm: Electronics

## SpecIF:DisciplineSoftware (SpecIF:TermPropertyValue)
- SpecIF:Domain: SpecIF:DomainRequirementsEngineering, SpecIF:DomainRequirementsEngineeringSRC
- SpecIF:TermStatus: SpecIF:LifecycleStatusDeprecated
- SpecIF:LocalTerm: Software

## SpecIF:DisciplineSafety (SpecIF:TermPropertyValue)
- SpecIF:Domain: SpecIF:DomainRequirementsEngineering, SpecIF:DomainRequirementsEngineeringSRC
- SpecIF:TermStatus: SpecIF:LifecycleStatusDeprecated
- SpecIF:LocalTerm: Safety

## SpecIF:NotApplicable (SpecIF:TermPropertyValue)
- SpecIF:Domain: SpecIF:DomainRequirementsEngineeringSRC
- SpecIF:TermStatus: SpecIF:LifecycleStatusReleased
- SpecIF:LocalTerm: not applicable, not-applicable, n/a

## SpecIF:InstantiationAuto (SpecIF:TermPropertyValue)
- dcterms:identifier: auto
- SpecIF:Revision: 1.2
- dcterms:description: The element class is instantiated automatically.

  This term defines a value of native property of a term. When a SpecIF class with the native property is generated, the default language of of the first value in 'Local Term' will be used. All others are ignored.
- SpecIF:TermStatus: SpecIF:LifecycleStatusReleased
- SpecIF:LocalTerm: auto

## SpecIF:InstantiationUser (SpecIF:TermPropertyValue)
- dcterms:identifier: user
- SpecIF:Revision: 1.2
- dcterms:description: The element class can be instantiated by a user.

  This term defines a value of native property of a term. When a SpecIF class with the native property is generated, the default language of of the first value in 'Local Term' will be used. All others are ignored.
- SpecIF:TermStatus: SpecIF:LifecycleStatusReleased
- SpecIF:LocalTerm: user

## SpecIF:TextFormatPlain (SpecIF:TermPropertyValue)
- dcterms:identifier: plain
- SpecIF:Revision: 1.2
- dcterms:description: This property value is plain text without formatting. Formatting by [Markdown](https://www.markdownguide.org/cheat-sheet/) is permissible.

  This term defines a value of native property of a term. When a SpecIF class with the native property is generated, the default language of of the first value in 'Local Term' will be used. All others are ignored.
- SpecIF:Domain: SpecIF:DomainOntology
- SpecIF:TermStatus: SpecIF:LifecycleStatusReleased
- SpecIF:LocalTerm: plain

## SpecIF:TextFormatXhtml (SpecIF:TermPropertyValue)
- dcterms:identifier: xhtml
- SpecIF:Revision: 1.2
- dcterms:description: This property value is text with XHTML formatting.

  This term defines a value of native property of a term. When a SpecIF class with the native property is generated, the default language of of the first value in 'Local Term' will be used. All others are ignored.
- SpecIF:Domain: SpecIF:DomainOntology
- SpecIF:TermStatus: SpecIF:LifecycleStatusReleased
- SpecIF:LocalTerm: plain

## ReqIF-WF.CustomerStatus.NotToEvaluate (SpecIF:TermPropertyValue)
- dcterms:description: The requirement is relevant, but no evaluation is expected.
  - Attribute can be set to this value during the first transmission
  - Attribute can be changed to this value during the assessment process to indicate that a requirement must no longer be evaluated
  - Supplier can react with [[ReqIF-WF.SupplierStatus.ToBeClarified]] if he has objections to the non-evaluation. Otherwise, the SupplierStatus remains empty and the workflow ends.
- SpecIF:Domain: SpecIF:DomainRequirementsEngineeringSRC
- SpecIF:TermStatus: SpecIF:LifecycleStatusReleased
- SpecIF:LocalTerm: not to evaluate, not-to-evaluate

## ReqIF-WF.CustomerStatus.ToEvaluate (SpecIF:TermPropertyValue)
- dcterms:description: For the corresponding object an evaluation is expected by the supplier.
  - Attribute can be set to this value during the first transmission
  - Attribute can be changed to this value during the assessment process to indicate that a requirement has been modified and must be re-evaluated
- SpecIF:Domain: SpecIF:DomainRequirementsEngineeringSRC
- SpecIF:TermStatus: SpecIF:LifecycleStatusReleased
- SpecIF:LocalTerm: to evaluate, to-evaluate

## ReqIF-WF.CustomerStatus.Accepted (SpecIF:TermPropertyValue)
- dcterms:description: The supplier evaluation is accepted by the customer.
- SpecIF:Domain: SpecIF:DomainRequirementsEngineeringSRC
- SpecIF:TermStatus: SpecIF:LifecycleStatusReleased
- SpecIF:LocalTerm: accepted

## ReqIF-WF.CustomerStatus.NotAccepted (SpecIF:TermPropertyValue)
- dcterms:description: The supplier evaluation is not accepted by the customer.
  - Setting this status terminates the evaluation for this object. The conflict must be solved in the further project course outside of this workflow.
- SpecIF:Domain: SpecIF:DomainRequirementsEngineeringSRC
- SpecIF:TermStatus: SpecIF:LifecycleStatusReleased
- SpecIF:LocalTerm: not accepted, not-accepted

## ReqIF-WF.CustomerStatus.ToBeClarified (SpecIF:TermPropertyValue)
- dcterms:description: The requirement has to be clarified with the supplier. Details in [[ReqIF-WF.CustomerComment]].
- SpecIF:Domain: SpecIF:DomainRequirementsEngineeringSRC
- SpecIF:TermStatus: SpecIF:LifecycleStatusReleased
- SpecIF:LocalTerm: to be clarified, to-clarify

## ReqIF-WF.CustomerStatus.ProposedToDiscard (SpecIF:TermPropertyValue)
- dcterms:description: The requirement is marked as invalid and has to be discarded.

  NOTE: This value is OPTIONAL until the new ReqIF-WF process is well-established in industry.
- SpecIF:Domain: SpecIF:DomainRequirementsEngineeringSRC
- SpecIF:TermStatus: SpecIF:LifecycleStatusReleased
- SpecIF:LocalTerm: proposed to discard

## ReqIF-WF.CustomerStatus.Discarded (SpecIF:TermPropertyValue)
- dcterms:description: The requirement has been marked explicitly as discarded by the customer.
- SpecIF:Domain: SpecIF:DomainRequirementsEngineeringSRC
- SpecIF:TermStatus: SpecIF:LifecycleStatusReleased
- SpecIF:LocalTerm: discarded

## ReqIF-WF.SupplierStatus.Agreed (SpecIF:TermPropertyValue)
- dcterms:description: The supplier accepts the requirement.
- SpecIF:Domain: SpecIF:DomainRequirementsEngineeringSRC
- SpecIF:TermStatus: SpecIF:LifecycleStatusReleased
- SpecIF:LocalTerm: agreed

## ReqIF-WF.SupplierStatus.NotAgreed (SpecIF:TermPropertyValue)
- dcterms:description: The supplier does not accept the requirement. Details must be declared in [[ReqIF-WF.SupplierComment]].
- SpecIF:Domain: SpecIF:DomainRequirementsEngineeringSRC
- SpecIF:TermStatus: SpecIF:LifecycleStatusReleased
- SpecIF:LocalTerm: not agreed, not-agreed

## ReqIF-WF.SupplierStatus.AgreedWithComment (SpecIF:TermPropertyValue)
- dcterms:description: The supplier accepts the requirement with restrictions. The restrictions are explained by the supplier in the comment attribute [[ReqIF-WF.SupplierComment]].
- SpecIF:Domain: SpecIF:DomainRequirementsEngineeringSRC
- SpecIF:TermStatus: SpecIF:LifecycleStatusReleased
- SpecIF:LocalTerm: agreed with comment, partly-agreed

## ReqIF-WF.SupplierStatus.ToBeClarified (SpecIF:TermPropertyValue)
- dcterms:description: The supplier requires clarification. The supplier must actively clarify the matter with the customer. Details must be declared in [[ReqIF-WF.SupplierComment]].
- SpecIF:Domain: SpecIF:DomainRequirementsEngineeringSRC
- SpecIF:TermStatus: SpecIF:LifecycleStatusReleased
- SpecIF:LocalTerm: to be clarified, to-clarify

## ReqIF-WF.SupplierStatus.DiscardedDeployed (SpecIF:TermPropertyValue)
- dcterms:description: The supplier confirms that he will not implement the discarded requirement.
- SpecIF:Domain: SpecIF:DomainRequirementsEngineeringSRC
- SpecIF:TermStatus: SpecIF:LifecycleStatusReleased
- SpecIF:LocalTerm: discarded

## oslc_cm:High (SpecIF:TermPropertyValue)
- SpecIF:Revision: 1.2
- dcterms:description: Highest priority, action on the change request highly recommended.
- SpecIF:Domain: SpecIF:DomainSystemModelIntegration, SpecIF:DomainProductLifecycleManagement
- SpecIF:TermStatus: SpecIF:LifecycleStatusEquivalent
- SpecIF:LocalTerm: high

## oslc_cm:Medium (SpecIF:TermPropertyValue)
- SpecIF:Revision: 1.2
- dcterms:description: Acting on the change request can wait, but not forever.
- SpecIF:Domain: SpecIF:DomainSystemModelIntegration, SpecIF:DomainProductLifecycleManagement
- SpecIF:TermStatus: SpecIF:LifecycleStatusEquivalent
- SpecIF:LocalTerm: medium

## oslc_cm:Low (SpecIF:TermPropertyValue)
- SpecIF:Revision: 1.2
- dcterms:description: Action on the change request can be safely deferred.
- SpecIF:Domain: SpecIF:DomainSystemModelIntegration, SpecIF:DomainProductLifecycleManagement
- SpecIF:TermStatus: SpecIF:LifecycleStatusEquivalent
- SpecIF:LocalTerm: low

## oslc_cm:PriorityUnassigned (SpecIF:TermPropertyValue)
- SpecIF:Revision: 1.2
- dcterms:description: The priority of the change request is intentionally not set.
- SpecIF:Domain: SpecIF:DomainSystemModelIntegration, SpecIF:DomainProductLifecycleManagement
- SpecIF:TermStatus: SpecIF:LifecycleStatusSubmitted
- SpecIF:LocalTerm: unassigned

## oslc_cm:Blocker (SpecIF:TermPropertyValue)
- SpecIF:Revision: 1.2
- dcterms:description: Severe problem. No workaround. Blocks development, test, or usage.
- SpecIF:Domain: SpecIF:DomainSystemModelIntegration, SpecIF:DomainAgileSystemDevelopment, SpecIF:DomainSystemTesting, SpecIF:DomainProductLifecycleManagement
- SpecIF:TermStatus: SpecIF:LifecycleStatusSubmitted
- SpecIF:LocalTerm: Blocker

## oslc_cm:Critical (SpecIF:TermPropertyValue)
- SpecIF:Revision: 1.2
- dcterms:description: Severe problem. No workaround.
- SpecIF:Domain: SpecIF:DomainSystemModelIntegration, SpecIF:DomainAgileSystemDevelopment, SpecIF:DomainSystemTesting, SpecIF:DomainProductLifecycleManagement
- SpecIF:TermStatus: SpecIF:LifecycleStatusSubmitted
- SpecIF:LocalTerm: Critical

## oslc_cm:Major (SpecIF:TermPropertyValue)
- SpecIF:Revision: 1.2
- dcterms:description: Prevents function from being used. There is a workaround.
- SpecIF:Domain: SpecIF:DomainSystemModelIntegration, SpecIF:DomainAgileSystemDevelopment, SpecIF:DomainSystemTesting, SpecIF:DomainProductLifecycleManagement
- SpecIF:TermStatus: SpecIF:LifecycleStatusSubmitted
- SpecIF:LocalTerm: Major

## oslc_cm:Normal (SpecIF:TermPropertyValue)
- SpecIF:Revision: 1.2
- dcterms:description: Affects non-critical functionality. There is a workaround.
- SpecIF:Domain: SpecIF:DomainSystemModelIntegration, SpecIF:DomainAgileSystemDevelopment, SpecIF:DomainSystemTesting, SpecIF:DomainProductLifecycleManagement
- SpecIF:TermStatus: SpecIF:LifecycleStatusSubmitted
- SpecIF:LocalTerm: Normal

## oslc_cm:Minor (SpecIF:TermPropertyValue)
- SpecIF:Revision: 1.2
- dcterms:description: Minimal impact.
- SpecIF:Domain: SpecIF:DomainSystemModelIntegration, SpecIF:DomainAgileSystemDevelopment, SpecIF:DomainSystemTesting, SpecIF:DomainProductLifecycleManagement
- SpecIF:TermStatus: SpecIF:LifecycleStatusSubmitted
- SpecIF:LocalTerm: Minor

## oslc_cm:SeverityUnassigned (SpecIF:TermPropertyValue)
- SpecIF:Revision: 1.2
- dcterms:description: Intentionally set blank.
- SpecIF:Domain: SpecIF:DomainSystemModelIntegration, SpecIF:DomainAgileSystemDevelopment, SpecIF:DomainSystemTesting, SpecIF:DomainProductLifecycleManagement
- SpecIF:TermStatus: SpecIF:LifecycleStatusSubmitted
- SpecIF:LocalTerm: Unassigned

## oslc_cm:Closed (SpecIF:TermPropertyValue)
- SpecIF:Revision: 1.2
- dcterms:description: Completely done, no further fixes or fix verification is needed.
- SpecIF:Domain: SpecIF:DomainAgileSystemDevelopment, SpecIF:DomainSystemTesting, SpecIF:DomainProductLifecycleManagement
- SpecIF:TermStatus: SpecIF:LifecycleStatusSubmitted
- SpecIF:LocalTerm: closed

## oslc_cm:Inprogress (SpecIF:TermPropertyValue)
- SpecIF:Revision: 1.2
- dcterms:description: Active work is occurring.
- SpecIF:Domain: SpecIF:DomainAgileSystemDevelopment, SpecIF:DomainSystemTesting, SpecIF:DomainProductLifecycleManagement
- SpecIF:TermStatus: SpecIF:LifecycleStatusSubmitted
- SpecIF:LocalTerm: in progress

## oslc_cm:Fixed (SpecIF:TermPropertyValue)
- SpecIF:Revision: 1.2
- dcterms:description: The issue is resolved or fixed but the resolution or fix has not yet been verified.
- SpecIF:Domain: SpecIF:DomainAgileSystemDevelopment, SpecIF:DomainSystemTesting, SpecIF:DomainProductLifecycleManagement
- SpecIF:TermStatus: SpecIF:LifecycleStatusSubmitted
- SpecIF:LocalTerm: Fixed

## oslc_cm:Approved (SpecIF:TermPropertyValue)
- SpecIF:Revision: 1.2
- dcterms:description: The resolution or fix is approved and can be delivered.
- SpecIF:Domain: SpecIF:DomainAgileSystemDevelopment, SpecIF:DomainSystemTesting, SpecIF:DomainProductLifecycleManagement
- SpecIF:TermStatus: SpecIF:LifecycleStatusSubmitted
- SpecIF:LocalTerm: Approved

## oslc_cm:Reviewed (SpecIF:TermPropertyValue)
- SpecIF:Revision: 1.2
- dcterms:description: The resolution or fix has been reviewed.
- SpecIF:Domain: SpecIF:DomainAgileSystemDevelopment, SpecIF:DomainSystemTesting, SpecIF:DomainProductLifecycleManagement
- SpecIF:TermStatus: SpecIF:LifecycleStatusSubmitted
- SpecIF:LocalTerm: Reviewed

## oslc_cm:Verified (SpecIF:TermPropertyValue)
- SpecIF:Revision: 1.2
- dcterms:description: The resolution or the fix is verified.
- SpecIF:Domain: SpecIF:DomainAgileSystemDevelopment, SpecIF:DomainSystemTesting, SpecIF:DomainProductLifecycleManagement
- SpecIF:TermStatus: SpecIF:LifecycleStatusSubmitted
- SpecIF:LocalTerm: Verified

## Statements
- SpecIF:satisfies SpecIF:isSynonymOfStatement oslc_rm:satisfies
- SpecIF:SubClass SpecIF:isSynonymOfProperty dcterms:type
- oslc_rm:satisfiedBy SpecIF:isAntonymOfStatement oslc_rm:satisfies
- oslc_rm:elaboratedBy SpecIF:isAntonymOfStatement oslc_rm:elaborates
- oslc_rm:specifiedBy SpecIF:isAntonymOfStatement oslc_rm:specifies
- oslc_rm:decomposedBy SpecIF:isAntonymOfStatement oslc_rm:decomposes
- oslc_rm:constrainedBy SpecIF:isAntonymOfStatement oslc_rm:constrains
- SpecIF:follows SpecIF:isAntonymOfStatement SpecIF:precedes
- SpecIF:sameAs SpecIF:isSynonymOfStatement owl:sameAs
- SpecIF:Id SpecIF:isSynonymOfProperty dcterms:identifier
- SpecIF:createdBy SpecIF:isSynonymOfProperty dcterms:creator
- SpecIF:createdAt SpecIF:isSynonymOfProperty dcterms:created
- SpecIF:changedAt SpecIF:isSynonymOfProperty dcterms:modified
- SpecIF:Creation SpecIF:isSynonymOfProperty SpecIF:Instantiation
- SpecIF:Source SpecIF:isSynonymOfProperty SpecIF:hasSubject
- SpecIF:Target SpecIF:isSynonymOfProperty SpecIF:hasObject
- IREB:RequirementTypeFunction SpecIF:isSynonymOfValue IREB:FunctionalRequirement
- IREB:RequirementTypeQuality SpecIF:isSynonymOfValue IREB:QualityRequirement
- IREB:RequirementTypeConstraint SpecIF:isSynonymOfValue IREB:Constraint
- SpecIF:isInverseOf SpecIF:isSynonymOfStatement SpecIF:isAntonymOf
- SpecIF:Stereotype SpecIF:isSynonymOfProperty uml:Stereotype
- uml:Stereotype SpecIF:isSynonymOfProperty dcterms:type
- SpecIF:SubClass SpecIF:isSynonymOfProperty uml:Stereotype
- FMC:Actor SpecIF:isEligibleAsSubject SpecIF:reads
- FMC:State SpecIF:isEligibleAsObject SpecIF:reads
- FMC:Actor SpecIF:isEligibleAsSubject SpecIF:writes
- FMC:State SpecIF:isEligibleAsObject SpecIF:writes
- FMC:Actor SpecIF:isEligibleAsSubject SpecIF:stores
- FMC:State SpecIF:isEligibleAsObject SpecIF:stores
- SpecIF:signals SpecIF:isSpecializationOfStatement SpecIF:precedes
- SpecIF:triggers SpecIF:isSpecializationOfStatement SpecIF:precedes
- FMC:receivesFrom SpecIF:isAntonymOfStatement FMC:sendsTo
- FMC:sendsTo SpecIF:isSpecializationOfStatement FMC:communicatesWith
- FMC:receivesFrom SpecIF:isSpecializationOfStatement FMC:communicatesWith
- FMC:Actor SpecIF:isEligibleAsSubject SpecIF:serves
- FMC:Actor SpecIF:isEligibleAsObject SpecIF:serves
- HIS:OemStatus SpecIF:isSynonymOfProperty ReqIF-WF.CustomerStatus
- HIS:SupplierComment SpecIF:isSynonymOfProperty ReqIF-WF.SupplierComment
- HIS:SupplierStatus SpecIF:isSynonymOfProperty ReqIF-WF.SupplierStatus
- HIS:OemComment SpecIF:isSynonymOfProperty ReqIF-WF.CustomerComment
- W3C:Vocabulary SpecIF:isSynonymOfResource W3C:Ontology
- SpecIF:Priority SpecIF:hasEnumValue SpecIF:priorityHigh
- SpecIF:Priority SpecIF:hasEnumValue SpecIF:priorityRatherHigh
- SpecIF:Priority SpecIF:hasEnumValue SpecIF:priorityMedium
- SpecIF:Priority SpecIF:hasEnumValue SpecIF:priorityRatherLow
- SpecIF:Priority SpecIF:hasEnumValue SpecIF:priorityLow
- SpecIF:LifecycleStatus SpecIF:hasEnumValue SpecIF:LifecycleStatusInitial
- SpecIF:LifecycleStatus SpecIF:hasEnumValue SpecIF:LifecycleStatusDrafted
- SpecIF:LifecycleStatus SpecIF:hasEnumValue SpecIF:LifecycleStatusSubmitted
- SpecIF:LifecycleStatus SpecIF:hasEnumValue SpecIF:LifecycleStatusApproved
- SpecIF:LifecycleStatus SpecIF:hasEnumValue SpecIF:LifecycleStatusReady
- SpecIF:LifecycleStatus SpecIF:hasEnumValue SpecIF:LifecycleStatusDone
- SpecIF:LifecycleStatus SpecIF:hasEnumValue SpecIF:LifecycleStatusValidated
- SpecIF:LifecycleStatus SpecIF:hasEnumValue SpecIF:LifecycleStatusReleased
- SpecIF:LifecycleStatus SpecIF:hasEnumValue SpecIF:LifecycleStatusDeprecated
- SpecIF:LifecycleStatus SpecIF:hasEnumValue SpecIF:LifecycleStatusWithdrawn
- SpecIF:LifecycleStatus SpecIF:hasEnumValue SpecIF:LifecycleStatusPostponed
- SpecIF:LifecycleStatus SpecIF:hasEnumValue SpecIF:LifecycleStatusRejected
- IREB:Requirement SpecIF:isEligibleAsSubject IREB:refines
- IREB:Requirement SpecIF:isEligibleAsObject IREB:refines
- SpecIF:Paragraph SpecIF:hasProperty dcterms:title
- SpecIF:Paragraph SpecIF:hasProperty dcterms:description
- SpecIF:commentRefersTo SpecIF:isSpecializationOfStatement SpecIF:refersTo
- SpecIF:Comment SpecIF:isEligibleAsSubject SpecIF:commentRefersTo
- SpecIF:Hierarchy SpecIF:hasProperty dcterms:title
- SpecIF:Hierarchy SpecIF:hasProperty dcterms:description
- SpecIF:Hierarchy SpecIF:hasProperty dcterms:type
- SpecIF:View SpecIF:isSpecializationOfResource SpecIF:Paragraph
- FMC:Plan SpecIF:isSynonymOfResource SpecIF:View
- SpecIF:Diagram SpecIF:isSynonymOfResource SpecIF:View
- SpecIF:View SpecIF:hasProperty SpecIF:Notation
- SpecIF:Heading SpecIF:isSpecializationOfResource SpecIF:Paragraph
- SpecIF:ModelElement SpecIF:hasProperty dcterms:title
- SpecIF:ModelElement SpecIF:hasProperty dcterms:description
- SpecIF:ModelElement SpecIF:hasProperty dcterms:type
- SpecIF:View SpecIF:isEligibleAsSubject SpecIF:shows
- SpecIF:Comment SpecIF:hasProperty dcterms:description
- IREB:Requirement SpecIF:isSpecializationOfResource SpecIF:Paragraph
- IREB:Requirement SpecIF:hasProperty SpecIF:Priority
- SpecIF:Feature SpecIF:isSpecializationOfResource SpecIF:Paragraph
- SpecIF:Feature SpecIF:hasProperty SpecIF:Priority
- ReqIF-WF.Requirement SpecIF:isSpecializationOfResource IREB:Requirement
- ReqIF-WF.Requirement SpecIF:hasProperty ReqIF-WF.SupplierStatus
- ReqIF-WF.Requirement SpecIF:hasProperty ReqIF-WF.SupplierComment
- ReqIF-WF.Requirement SpecIF:hasProperty ReqIF-WF.CustomerStatus
- ReqIF-WF.Requirement SpecIF:hasProperty ReqIF-WF.CustomerComment
- ReqIF-WF.SupplierStatus SpecIF:hasEnumValue ReqIF-WF.SupplierStatus.ToBeClarified
- ReqIF-WF.SupplierStatus SpecIF:hasEnumValue ReqIF-WF.SupplierStatus.AgreedWithComment
- ReqIF-WF.SupplierStatus SpecIF:hasEnumValue ReqIF-WF.SupplierStatus.Agreed
- ReqIF-WF.SupplierStatus SpecIF:hasEnumValue ReqIF-WF.SupplierStatus.NotAgreed
- ReqIF-WF.SupplierStatus SpecIF:hasEnumValue ReqIF-WF.SupplierStatus.DiscardedDeployed
- ReqIF-WF.CustomerStatus SpecIF:hasEnumValue ReqIF-WF.CustomerStatus.ToEvaluate
- ReqIF-WF.CustomerStatus SpecIF:hasEnumValue ReqIF-WF.CustomerStatus.ToBeClarified
- ReqIF-WF.CustomerStatus SpecIF:hasEnumValue ReqIF-WF.CustomerStatus.NotAccepted
- ReqIF-WF.CustomerStatus SpecIF:hasEnumValue ReqIF-WF.CustomerStatus.Accepted
- ReqIF-WF.CustomerStatus SpecIF:hasEnumValue ReqIF-WF.CustomerStatus.NotToEvaluate
- ReqIF-WF.CustomerStatus SpecIF:hasEnumValue ReqIF-WF.CustomerStatus.ProposedToDiscard
- ReqIF-WF.CustomerStatus SpecIF:hasEnumValue ReqIF-WF.CustomerStatus.Discarded
- SpecIF:EngineeringDiscipline SpecIF:hasEnumValue SpecIF:EngineeringDisciplineMechanics
- SpecIF:EngineeringDiscipline SpecIF:hasEnumValue SpecIF:EngineeringDisciplineElectronics
- SpecIF:EngineeringDiscipline SpecIF:hasEnumValue SpecIF:EngineeringDisciplineSoftware
- SpecIF:EngineeringDiscipline SpecIF:hasEnumValue SpecIF:EngineeringDisciplineSafety
- SpecIF:EngineeringDiscipline SpecIF:hasEnumValue SpecIF:EngineeringDisciplineSystem
- SpecIF:TermResourceClass SpecIF:isSpecializationOfResource SpecIF:OntologyTerm
- SpecIF:TermStatementClass SpecIF:isSpecializationOfResource SpecIF:OntologyTerm
- SpecIF:TermPropertyClass SpecIF:isSpecializationOfResource SpecIF:OntologyTerm
- SpecIF:TermPropertyValue SpecIF:isSpecializationOfResource SpecIF:OntologyTerm
- bpmn:group SpecIF:isSynonymOfResource SpecIF:Collection
- oslc_rm:elaborates SpecIF:isSynonymOfStatement IREB:refines
- IREB:Requirement SpecIF:hasProperty IREB:RequirementType
- ReqIF-WF.Requirement SpecIF:isEligibleAsSubject IREB:refines
- ReqIF-WF.Requirement SpecIF:isEligibleAsObject IREB:refines
- IREB:Requirement SpecIF:isEligibleAsSubject SpecIF:duplicates
- ReqIF-WF.Requirement SpecIF:isEligibleAsSubject SpecIF:duplicates
- IREB:Requirement SpecIF:isEligibleAsObject SpecIF:duplicates
- ReqIF-WF.Requirement SpecIF:isEligibleAsObject SpecIF:duplicates
- IREB:Requirement SpecIF:isEligibleAsSubject SpecIF:contradicts
- ReqIF-WF.Requirement SpecIF:isEligibleAsSubject SpecIF:contradicts
- IREB:Requirement SpecIF:isEligibleAsObject SpecIF:contradicts
- ReqIF-WF.Requirement SpecIF:isEligibleAsObject SpecIF:contradicts
- SpecIF:Perspective SpecIF:isSynonymOfProperty SpecIF:StakeholderGroup
- IREB:Requirement SpecIF:hasProperty SpecIF:StakeholderGroup
- SpecIF:StakeholderGroup SpecIF:hasEnumValue SpecIF:StakeholderGroupRegulation
- SpecIF:StakeholderGroup SpecIF:hasEnumValue SpecIF:StakeholderGroupBusiness
- SpecIF:StakeholderGroup SpecIF:hasEnumValue SpecIF:StakeholderGroupUser
- SpecIF:StakeholderGroup SpecIF:hasEnumValue SpecIF:StakeholderGroupSystem
- SpecIF:StakeholderGroup SpecIF:hasEnumValue SpecIF:StakeholderGroupOperation
- SpecIF:Feature SpecIF:isSynonymOfResource IREB:Requirement
- IREB:RequirementType SpecIF:hasEnumValue SpecIF:Feature
- IREB:RequirementType SpecIF:hasEnumValue SpecIF:UserStory
- IREB:RequirementType SpecIF:hasEnumValue IREB:FunctionalRequirement
- IREB:RequirementType SpecIF:hasEnumValue IREB:QualityRequirement
- IREB:RequirementType SpecIF:hasEnumValue IREB:Constraint
- SpecIF:stores SpecIF:isSynonymOfStatement SpecIF:accesses
- SpecIF:reads SpecIF:isSpecializationOfStatement SpecIF:accesses
- SpecIF:writes SpecIF:isSpecializationOfStatement SpecIF:accesses
- FMC:modifies SpecIF:isSynonymOfStatement SpecIF:accesses
- FMC:Actor SpecIF:isEligibleAsSubject SpecIF:follows
- FMC:Actor SpecIF:isEligibleAsObject SpecIF:follows
- FMC:Actor SpecIF:isEligibleAsSubject SpecIF:precedes
- FMC:Actor SpecIF:isEligibleAsObject SpecIF:precedes
- FMC:Actor SpecIF:isEligibleAsSubject FMC:communicatesWith
- FMC:Actor SpecIF:isEligibleAsObject FMC:communicatesWith
- FMC:Actor SpecIF:isEligibleAsSubject FMC:sendsTo
- FMC:Actor SpecIF:isEligibleAsObject FMC:sendsTo
- FMC:Actor SpecIF:isEligibleAsSubject FMC:receivesFrom
- FMC:Actor SpecIF:isEligibleAsObject FMC:receivesFrom
- FMC:Actor SpecIF:isEligibleAsSubject SpecIF:accesses
- FMC:State SpecIF:isEligibleAsObject SpecIF:accesses
- IREB:Requirement SpecIF:isEligibleAsSubject SpecIF:dependsOn
- ReqIF-WF.Requirement SpecIF:isEligibleAsSubject SpecIF:dependsOn
- IREB:Requirement SpecIF:isEligibleAsObject SpecIF:dependsOn
- ReqIF-WF.Requirement SpecIF:isEligibleAsObject SpecIF:dependsOn
- IREB:Requirement SpecIF:isEligibleAsSubject sysml:Trace
- ReqIF-WF.Requirement SpecIF:isEligibleAsSubject sysml:Trace
- IREB:Requirement SpecIF:isEligibleAsObject sysml:Trace
- ReqIF-WF.Requirement SpecIF:isEligibleAsObject sysml:Trace
- IREB:Requirement SpecIF:isEligibleAsSubject sysml:Derive
- ReqIF-WF.Requirement SpecIF:isEligibleAsSubject sysml:Derive
- IREB:Requirement SpecIF:isEligibleAsObject sysml:Derive
- ReqIF-WF.Requirement SpecIF:isEligibleAsObject sysml:Derive
- FMC:Actor SpecIF:isEligibleAsSubject uml:extends
- FMC:Actor SpecIF:isEligibleAsObject uml:extends
- FMC:Actor SpecIF:isEligibleAsSubject sysml:includes
- FMC:Actor SpecIF:isEligibleAsObject sysml:includes
- FMC:Actor SpecIF:isEligibleAsSubject SpecIF:contains
- FMC:State SpecIF:isEligibleAsSubject SpecIF:contains
- FMC:Actor SpecIF:isEligibleAsObject SpecIF:contains
- FMC:State SpecIF:isEligibleAsObject SpecIF:contains
- FMC:Event SpecIF:isEligibleAsObject SpecIF:contains
- SpecIF:Collection SpecIF:isEligibleAsSubject SpecIF:contains
- FMC:Actor SpecIF:isEligibleAsSubject FMC:contains
- FMC:State SpecIF:isEligibleAsSubject FMC:contains
- FMC:Actor SpecIF:isEligibleAsObject FMC:contains
- FMC:State SpecIF:isEligibleAsObject FMC:contains
- FMC:Event SpecIF:isEligibleAsObject FMC:contains
- SpecIF:Collection SpecIF:isEligibleAsObject SpecIF:contains
- oslc_rm:decomposedBy SpecIF:isSynonymOfStatement uml:Composition
- SpecIF:contains SpecIF:hasProperty dcterms:type
- FMC:Plan SpecIF:isSpecializationOfResource SpecIF:Paragraph
- ReqIF.Text SpecIF:isSynonymOfProperty dcterms:description
- ReqIF.Name SpecIF:isSynonymOfProperty dcterms:title
- ReqIF.ForeignID SpecIF:isSynonymOfProperty dcterms:identifier
- ReqIF.ForeignState SpecIF:isSynonymOfProperty SpecIF:LifecycleStatus
- ReqIF.Category SpecIF:isSynonymOfProperty dcterms:type
- ArchiMate:Viewpoint SpecIF:isSpecializationOfResource SpecIF:Paragraph
- ArchiMate:Viewpoint SpecIF:hasProperty SpecIF:Notation
- ArchiMate:Viewpoint SpecIF:isSynonymOfResource SpecIF:View
- FMC:Plan SpecIF:hasProperty SpecIF:Notation
- SpecIF:Outline SpecIF:hasProperty SpecIF:LifecycleStatus
- SpecIF:Hierarchy SpecIF:hasProperty SpecIF:LifecycleStatus
- SpecIF:BusinessProcess SpecIF:isSpecializationOfResource SpecIF:View
- SpecIF: SpecIF:isNamespace SpecIF:Paragraph
- SpecIF: SpecIF:isNamespace SpecIF:Heading
- SpecIF: SpecIF:isNamespace SpecIF:View
- ArchiMate: SpecIF:isNamespace ArchiMate:Viewpoint
- SpecIF: SpecIF:isNamespace SpecIF:Diagram
- SpecIF: SpecIF:isNamespace SpecIF:Feature
- IREB: SpecIF:isNamespace IREB:Requirement
- ReqIF-WF. SpecIF:isNamespace ReqIF-WF.Requirement
- SpecIF: SpecIF:isNamespace SpecIF:ModelElement
- FMC: SpecIF:isNamespace FMC:Plan
- FMC: SpecIF:isNamespace FMC:Actor
- FMC: SpecIF:isNamespace FMC:State
- FMC: SpecIF:isNamespace FMC:Event
- SpecIF: SpecIF:isNamespace SpecIF:Collection
- ReqIF-WF. SpecIF:isNamespace ReqIF-WF.CustomerComment
- ReqIF-WF. SpecIF:isNamespace ReqIF-WF.CustomerStatus
- ReqIF-WF. SpecIF:isNamespace ReqIF-WF.SupplierComment
- ReqIF-WF. SpecIF:isNamespace ReqIF-WF.SupplierStatus
- ReqIF. SpecIF:isNamespace ReqIF.Category
- ReqIF. SpecIF:isNamespace ReqIF.ForeignID
- ReqIF. SpecIF:isNamespace ReqIF.ForeignState
- ReqIF. SpecIF:isNamespace ReqIF.Name
- ReqIF. SpecIF:isNamespace ReqIF.Text
- FMC: SpecIF:isNamespace FMC:contains
- FMC: SpecIF:isNamespace FMC:modifies
- IREB: SpecIF:isNamespace IREB:Constraint
- IREB: SpecIF:isNamespace IREB:Stakeholder
- IREB: SpecIF:isNamespace IREB:Risk
- IREB: SpecIF:isNamespace IREB:FunctionalRequirement
- IREB: SpecIF:isNamespace IREB:QualityRequirement
- IREB: SpecIF:isNamespace IREB:RequirementType
- IREB: SpecIF:isNamespace IREB:RequirementTypeConstraint
- IREB: SpecIF:isNamespace IREB:RequirementTypeFunction
- IREB: SpecIF:isNamespace IREB:RequirementTypeQuality
- IREB: SpecIF:isNamespace IREB:refines
- bpmn: SpecIF:isNamespace bpmn:group
- bpmn: SpecIF:isNamespace bpmn:processStep
- bpmn: SpecIF:isNamespace bpmn:timer
- bpmn: SpecIF:isNamespace bpmn:startEvent
- bpmn: SpecIF:isNamespace bpmn:intermediateEvent
- bpmn: SpecIF:isNamespace bpmn:endEvent
- bpmn: SpecIF:isNamespace bpmn:join
- ArchiMate: SpecIF:isNamespace ArchiMate:Uniting
- foaf: SpecIF:isNamespace foaf:Person
- SpecIF: SpecIF:isNamespace SpecIF:Glossary
- SpecIF: SpecIF:isNamespace SpecIF:Hierarchy
- SpecIF: SpecIF:isNamespace SpecIF:Diagram
- SpecIF: SpecIF:isNamespace SpecIF:Damage
- SpecIF: SpecIF:isNamespace SpecIF:Benefit
- SpecIF: SpecIF:isNamespace SpecIF:BillOfMaterials
- SpecIF: SpecIF:isNamespace SpecIF:BusinessProcess
- SpecIF: SpecIF:isNamespace SpecIF:Category
- SpecIF: SpecIF:isNamespace SpecIF:Comment
- SpecIF: SpecIF:isNamespace SpecIF:DueDate
- SpecIF: SpecIF:isNamespace SpecIF:FitCriteria
- SpecIF: SpecIF:isNamespace SpecIF:LifecycleStatus
- SpecIF:Category SpecIF:isSynonymOfProperty dcterms:type
- SpecIF: SpecIF:isNamespace SpecIF:Revision
- ReqIF. SpecIF:isNamespace ReqIF.Revision
- ReqIF.Revision SpecIF:isSynonymOfProperty SpecIF:Revision
- ReqIF. SpecIF:isNamespace ReqIF.ForeignCreatedBy
- ReqIF.ForeignCreatedBy SpecIF:isSynonymOfProperty dcterms:creator
- ReqIF. SpecIF:isNamespace ReqIF.ChapterName
- W3C: SpecIF:isNamespace W3C:Ontology
- W3C: SpecIF:isNamespace W3C:Vocabulary
- owl: SpecIF:isNamespace owl:sameAs
- dcterms: SpecIF:isNamespace dcterms:title
- dcterms: SpecIF:isNamespace dcterms:description
- dcterms: SpecIF:isNamespace dcterms:type
- dcterms: SpecIF:isNamespace dcterms:identifier
- dcterms: SpecIF:isNamespace dcterms:creator
- dcterms: SpecIF:isNamespace dcterms:created
- dcterms: SpecIF:isNamespace dcterms:modified
- dcterms: SpecIF:isNamespace dcterms:contributor
- dcterms: SpecIF:isNamespace dcterms:rightsHolder
- dcterms: SpecIF:isNamespace dcterms:rights
- dcterms: SpecIF:isNamespace dcterms:subject
- rdf: SpecIF:isNamespace rdf:type
- foaf:Person SpecIF:isSynonymOfResource schema:Person
- schema: SpecIF:isNamespace schema:Person
- schema: SpecIF:isNamespace schema:Organization
- schema: SpecIF:isNamespace schema:Role
- ReqIF. SpecIF:isNamespace ReqIF.ChapterNumber
- ReqIF. SpecIF:isNamespace ReqIF.Prefix
- ReqIF. SpecIF:isNamespace ReqIF.Description
- ReqIF. SpecIF:isNamespace ReqIF.FitCriteria
- ReqIF. SpecIF:isNamespace ReqIF.ChangeDescription
- ReqIF. SpecIF:isNamespace ReqIF.Project
- ReqIF. SpecIF:isNamespace ReqIF.AssociatedFiles
- ReqIF.Description SpecIF:isSynonymOfProperty dcterms:description
- ReqIF.FitCriteria SpecIF:isSynonymOfProperty SpecIF:FitCriteria
- dcterms: SpecIF:isNamespace oslc:serviceProvider
- oslc_rm: SpecIF:isNamespace oslc_rm:implementedBy
- oslc_rm:implementedBy SpecIF:isAntonymOfStatement oslc_rm:implements
- oslc_rm: SpecIF:isNamespace oslc_rm:implements
- SpecIF:implements SpecIF:isSynonymOfStatement oslc_rm:implements
- oslc_rm:validatedBy SpecIF:isAntonymOfStatement oslc_rm:validates
- oslc_rm: SpecIF:isNamespace oslc_rm:validatedBy
- oslc_rm: SpecIF:isNamespace oslc_rm:validates
- oslc_rm: SpecIF:isNamespace oslc_rm:decomposes
- oslc_rm: SpecIF:isNamespace oslc_rm:decomposedBy
- ArchiMate:Composition SpecIF:isSynonymOfStatement uml:Composition
- ArchiMate:Aggregation SpecIF:isSynonymOfStatement uml:Aggregation
- ArchiMate:Aggregation SpecIF:isSpecializationOfStatement ArchiMate:Uniting
- SpecIF:Requirement SpecIF:isSynonymOfResource IREB:Requirement
- SpecIF: SpecIF:isNamespace SpecIF:Requirement
- SpecIF:Perspective SpecIF:hasEnumValue SpecIF:PerspectiveBusiness
- SpecIF:Perspective SpecIF:hasEnumValue SpecIF:PerspectiveStakeholder
- SpecIF:Perspective SpecIF:hasEnumValue SpecIF:PerspectiveUser
- SpecIF:Perspective SpecIF:hasEnumValue SpecIF:PerspectiveOperator
- SpecIF:Perspective SpecIF:hasEnumValue SpecIF:PerspectiveSystem
- SpecIF:PerspectiveBusiness SpecIF:isSynonymOfValue SpecIF:StakeholderGroupBusiness
- SpecIF:PerspectiveUser SpecIF:isSynonymOfValue SpecIF:StakeholderGroupUser
- SpecIF:PerspectiveOperator SpecIF:isSynonymOfValue SpecIF:StakeholderGroupOperation
- SpecIF:PerspectiveSystem SpecIF:isSynonymOfValue SpecIF:StakeholderGroupSystem
- IREB:Risk SpecIF:hasProperty SpecIF:Probability
- IREB:Risk SpecIF:hasProperty SpecIF:Impact
- IREB:Requirement SpecIF:isEligibleAsObject oslc_rm:satisfies
- ReqIF-WF.Requirement SpecIF:isEligibleAsObject oslc_rm:satisfies
- FMC:Actor SpecIF:isEligibleAsSubject oslc_rm:satisfies
- FMC:State SpecIF:isEligibleAsSubject oslc_rm:satisfies
- FMC:Event SpecIF:isEligibleAsSubject oslc_rm:satisfies
- SpecIF:Collection SpecIF:isEligibleAsSubject oslc_rm:satisfies
- IREB:Requirement SpecIF:isEligibleAsSubject oslc_rm:satisfiedBy
- ReqIF-WF.Requirement SpecIF:isEligibleAsSubject oslc_rm:satisfiedBy
- FMC:Actor SpecIF:isEligibleAsObject oslc_rm:satisfiedBy
- FMC:State SpecIF:isEligibleAsObject oslc_rm:satisfiedBy
- FMC:Event SpecIF:isEligibleAsObject oslc_rm:satisfiedBy
- SpecIF:Collection SpecIF:isEligibleAsObject oslc_rm:satisfiedBy
- ArchiMate:Access SpecIF:isSynonymOfStatement SpecIF:accesses
- ArchiMate: SpecIF:isNamespace ArchiMate:Realization
- SpecIF:realizedBy SpecIF:isAntonymOfStatement ArchiMate:Realization
- ArchiMate:Realization SpecIF:isSpecializationOfStatement ArchiMate:Uniting
- FMC:Actor SpecIF:isEligibleAsSubject ArchiMate:Serving
- FMC:Actor SpecIF:isEligibleAsObject ArchiMate:Serving
- ArchiMate: SpecIF:isNamespace ArchiMate:Serving
- ArchiMate: SpecIF:isNamespace ArchiMate:Assignment
- ArchiMate:Assignment SpecIF:isSpecializationOfStatement ArchiMate:Uniting
- uml: SpecIF:isNamespace uml:Association
- uml: SpecIF:isNamespace uml:Aggregation
- SpecIF:issueRefersTo SpecIF:isSpecializationOfStatement SpecIF:refersTo
- SpecIF: SpecIF:isNamespace SpecIF:Size
- SpecIF:Size SpecIF:hasEnumValue SpecIF:sizeXL
- SpecIF:Size SpecIF:hasEnumValue SpecIF:sizeL
- SpecIF:Size SpecIF:hasEnumValue SpecIF:sizeM
- SpecIF:Size SpecIF:hasEnumValue SpecIF:sizeS
- SpecIF:Size SpecIF:hasEnumValue SpecIF:sizeXS
- SpecIF:DisciplineSystem SpecIF:isSynonymOfValue SpecIF:EngineeringDisciplineSystem
- SpecIF:DisciplineSystemEngineering SpecIF:isSynonymOfValue SpecIF:EngineeringDisciplineSystem
- SpecIF:DisciplineMechanics SpecIF:isSynonymOfValue SpecIF:EngineeringDisciplineMechanics
- SpecIF:DisciplineElectronics SpecIF:isSynonymOfValue SpecIF:EngineeringDisciplineElectronics
- SpecIF:DisciplineSoftware SpecIF:isSynonymOfValue SpecIF:EngineeringDisciplineSoftware
- SpecIF:DisciplineSafety SpecIF:isSynonymOfValue SpecIF:EngineeringDisciplineSafety
- SpecIF: SpecIF:isNamespace SpecIF:Folder
- SpecIF:Folder SpecIF:isSynonymOfResource SpecIF:Heading
- IREB: SpecIF:isNamespace IREB:refinedBy
- IREB:refinedBy SpecIF:isAntonymOfStatement IREB:refines
- SpecIF: SpecIF:isNamespace SpecIF:Information
- SpecIF:Information SpecIF:isSynonymOfResource SpecIF:Paragraph
- uml: SpecIF:isNamespace uml:Generalization
- SpecIF: SpecIF:isNamespace SpecIF:isSpecializationOf
- SpecIF: SpecIF:isNamespace SpecIF:isGeneralizationOf
- SpecIF:isGeneralizationOf SpecIF:isSynonymOfStatement uml:Generalization
- IR: SpecIF:isNamespace IR:refersTo
- IR:refersTo SpecIF:isSynonymOfStatement SpecIF:refersTo
- IR:Annotation SpecIF:isEligibleAsObject IR:approves
- IR:Annotation SpecIF:isEligibleAsObject IR:opposes
- IR: SpecIF:isNamespace IR:inheritsFrom
- IR: SpecIF:isNamespace IR:approves
- IR: SpecIF:isNamespace IR:opposes
- SpecIF: SpecIF:isNamespace SpecIF:realizes
- SpecIF: SpecIF:isNamespace SpecIF:inheritsFrom
- SpecIF: SpecIF:isNamespace SpecIF:Id
- SpecIF: SpecIF:isNamespace SpecIF:Type
- SpecIF: SpecIF:isNamespace SpecIF:Stereotype
- SpecIF:Type SpecIF:isSynonymOfProperty dcterms:type
- SpecIF: SpecIF:isNamespace SpecIF:LifecycleStatusReleased
- SpecIF: SpecIF:isNamespace SpecIF:Instantiation
- ReqIF-WF. SpecIF:isNamespace ReqIF-WF.Customer
- ReqIF-WF. SpecIF:isNamespace ReqIF-WF.Supplier
- SpecIF: SpecIF:isNamespace SpecIF:TermStatus
- SpecIF:TermStatus SpecIF:hasEnumValue SpecIF:LifecycleStatusExperimental
- SpecIF:TermStatus SpecIF:hasEnumValue SpecIF:LifecycleStatusSubmitted
- SpecIF: SpecIF:isNamespace SpecIF:OntologyTerm
- SpecIF:OntologyTerm SpecIF:hasProperty dcterms:identifier
- SpecIF:OntologyTerm SpecIF:hasProperty SpecIF:Revision
- SpecIF:OntologyTerm SpecIF:hasProperty SpecIF:Term
- SpecIF:OntologyTerm SpecIF:hasProperty dcterms:description
- SpecIF:OntologyTerm SpecIF:hasProperty SpecIF:Domain
- SpecIF:OntologyTerm SpecIF:hasProperty SpecIF:TermStatus
- SpecIF:OntologyTerm SpecIF:hasProperty SpecIF:LocalTerm
- SpecIF: SpecIF:isNamespace SpecIF:TermPropertyClassURI
- SpecIF:TermPropertyClassURI SpecIF:isSpecializationOfResource SpecIF:TermPropertyClass
- SpecIF:TermPropertyClassDuration SpecIF:isSpecializationOfResource SpecIF:TermPropertyClass
- SpecIF:TermPropertyClassTimestamp SpecIF:isSpecializationOfResource SpecIF:TermPropertyClass
- SpecIF:TermPropertyClassReal SpecIF:isSpecializationOfResource SpecIF:TermPropertyClass
- SpecIF:TermPropertyClassInteger SpecIF:isSpecializationOfResource SpecIF:TermPropertyClass
- SpecIF:TermPropertyClassBoolean SpecIF:isSpecializationOfResource SpecIF:TermPropertyClass
- SpecIF:TermPropertyClassString SpecIF:isSpecializationOfResource SpecIF:TermPropertyClass
- SpecIF: SpecIF:isNamespace SpecIF:TermPropertyClassString
- SpecIF: SpecIF:isNamespace SpecIF:TermPropertyClassBoolean
- SpecIF: SpecIF:isNamespace SpecIF:TermPropertyClassInteger
- SpecIF: SpecIF:isNamespace SpecIF:TermPropertyClassReal
- SpecIF: SpecIF:isNamespace SpecIF:TermPropertyClassTimestamp
- SpecIF: SpecIF:isNamespace SpecIF:Namespace
- ReqIF.ChapterName SpecIF:isSynonymOfProperty dcterms:title
- IREB:RequirementType SpecIF:hasEnumValue SpecIF:PainPoint
- SpecIF: SpecIF:isNamespace SpecIF:isPluralOf
- SpecIF: SpecIF:isNamespace SpecIF:relates
- SpecIF: SpecIF:isNamespace SpecIF:Resource
- SpecIF: SpecIF:isNamespace SpecIF:Statement
- SpecIF:contains SpecIF:isSpecializationOfStatement SpecIF:relates
- SpecIF:accesses SpecIF:isSpecializationOfStatement SpecIF:relates
- SpecIF: SpecIF:isNamespace SpecIF:hasEnumValue
- SpecIF:TermPropertyClassString SpecIF:isEligibleAsSubject SpecIF:hasEnumValue
- SpecIF:TermResourceClass SpecIF:isEligibleAsObject SpecIF:hasEnumValue
- SpecIF:TermStatementClass SpecIF:isEligibleAsObject SpecIF:hasEnumValue
- SpecIF:TermPropertyValue SpecIF:isEligibleAsObject SpecIF:hasEnumValue
- SpecIF:Discipline SpecIF:isSynonymOfProperty SpecIF:EngineeringDiscipline
- SpecIF:Status SpecIF:isSynonymOfProperty SpecIF:LifecycleStatus
- SpecIF: SpecIF:isNamespace SpecIF:Editor
- ReqIF. SpecIF:isNamespace ReqIF.ForeignModifiedOn
- ReqIF.ForeignModifiedOn SpecIF:isSynonymOfProperty dcterms:modified
- ReqIF. SpecIF:isNamespace ReqIF.ForeignModifiedBy
- ReqIF.ForeignModifiedBy SpecIF:isSynonymOfProperty SpecIF:changedBy
- ReqIF. SpecIF:isNamespace ReqIF.ForeignCreatedOn
- ReqIF.ForeignCreatedOn SpecIF:isSynonymOfProperty dcterms:created
- bpmn: SpecIF:isNamespace bpmn:Pool
- bpmn:Pool SpecIF:isSpecializationOfResource bpmn:Participant
- bpmn: SpecIF:isNamespace bpmn:Lane
- bpmn:Lane SpecIF:isSpecializationOfResource bpmn:Participant
- bpmn:Participant SpecIF:isSpecializationOfResource FMC:Actor
- bpmn:Lane SpecIF:isSynonymOfResource uml:Actor
- uml: SpecIF:isNamespace uml:Actor
- uml:Actor SpecIF:isSpecializationOfResource FMC:Actor
- SpecIF:BusinessProcess SpecIF:isSynonymOfResource bpmn:Process
- SpecIF:BusinessProcesses SpecIF:isPluralOfResource SpecIF:BusinessProcess
- SpecIF:BusinessProcesses SpecIF:isPluralOfResource bpmn:Process
- SpecIF: SpecIF:isNamespace SpecIF:Views
- SpecIF:Views SpecIF:isPluralOfResource SpecIF:View
- SpecIF: SpecIF:isNamespace SpecIF:BusinessProcesses
- sysml:extends SpecIF:isSynonymOfStatement uml:extends
- sysml: SpecIF:isNamespace sysml:extends
- uml: SpecIF:isNamespace uml:extends
- DDP: SpecIF:isNamespace DDP:Source
- DDP:Source SpecIF:isSpecializationOfResource SpecIF:Paragraph
- DDP:Source SpecIF:hasProperty SpecIF:ModelFile
- ArchiMate:Viewpoint SpecIF:hasProperty SpecIF:Diagram
- FMC:Plan SpecIF:hasProperty SpecIF:Diagram
- DDP: SpecIF:isNamespace DDP:definedBy
- DDP:Source SpecIF:isEligibleAsObject DDP:definedBy
- schema: SpecIF:isNamespace schema:name
- schema: SpecIF:isNamespace schema:description
- schema:description SpecIF:isSynonymOfProperty dcterms:description
- dcterms: SpecIF:isNamespace dcterms:hasPart
- dcterms: SpecIF:isNamespace dcterms:isPartOf
- dcterms:isPartOf SpecIF:isAntonymOfStatement dcterms:hasPart
- xs: SpecIF:isNamespace xs:boolean
- xs: SpecIF:isNamespace xs:integer
- xs: SpecIF:isNamespace xs:double
- xs: SpecIF:isNamespace xs:unsignedByte
- xs: SpecIF:isNamespace xs:dateTime
- xs: SpecIF:isNamespace xs:duration
- xs: SpecIF:isNamespace xs:anyURI
- SpecIF: SpecIF:isNamespace SpecIF:isRequired
- SpecIF: SpecIF:isNamespace SpecIF:isUndirected
- SpecIF: SpecIF:isNamespace SpecIF:isHeading
- SpecIF: SpecIF:isNamespace SpecIF:singleLanguage
- SpecIF: SpecIF:isNamespace SpecIF:multiple
- oslc_cm: SpecIF:isNamespace oslc_cm:Status
- oslc_cm:Status SpecIF:hasEnumValue oslc_cm:Closed
- oslc_cm:Status SpecIF:hasEnumValue oslc_cm:Inprogress
- oslc_cm:Status SpecIF:hasEnumValue oslc_cm:Fixed
- oslc_cm:Status SpecIF:hasEnumValue oslc_cm:Approved
- oslc_cm:Status SpecIF:hasEnumValue oslc_cm:Reviewed
- oslc_cm:Status SpecIF:hasEnumValue oslc_cm:Verified
- oslc_cm: SpecIF:isNamespace oslc_cm:Priority
- oslc_cm:Priority SpecIF:hasEnumValue oslc_cm:High
- oslc_cm:Priority SpecIF:hasEnumValue oslc_cm:Medium
- oslc_cm:Priority SpecIF:hasEnumValue oslc_cm:Low
- oslc_cm:Priority SpecIF:hasEnumValue oslc_cm:PriorityUnassigned
- oslc_cm: SpecIF:isNamespace oslc_cm:Severity
- oslc_cm:Severity SpecIF:hasEnumValue oslc_cm:Blocker
- oslc_cm:Severity SpecIF:hasEnumValue oslc_cm:Critical
- oslc_cm:Severity SpecIF:hasEnumValue oslc_cm:Major
- oslc_cm:Severity SpecIF:hasEnumValue oslc_cm:Normal
- oslc_cm:Severity SpecIF:hasEnumValue oslc_cm:Minor
- oslc_cm:Severity SpecIF:hasEnumValue oslc_cm:SeverityUnassigned
- IREB:Requirement SpecIF:isEligibleAsSubject dcterms:replaces
- ReqIF-WF.Requirement SpecIF:isEligibleAsSubject dcterms:replaces
- IREB:Requirement SpecIF:isEligibleAsObject dcterms:replaces
- ReqIF-WF.Requirement SpecIF:isEligibleAsObject dcterms:replaces
- SpecIF: SpecIF:isNamespace SpecIF:duplicates
- SpecIF: SpecIF:isNamespace SpecIF:contradicts
- dcterms: SpecIF:isNamespace dcterms:replaces
- dcterms:replaces SpecIF:hasProperty dcterms:description
- bpmn:Process SpecIF:isSpecializationOfResource SpecIF:View
- SpecIF:BusinessProcesses SpecIF:isSpecializationOfResource SpecIF:Views
- schema:Person SpecIF:isSpecializationOfResource SpecIF:Paragraph
- schema:Role SpecIF:isSpecializationOfResource SpecIF:Paragraph
- schema:Organization SpecIF:isSpecializationOfResource SpecIF:Paragraph
- SpecIF:UserRole SpecIF:isSpecializationOfResource schema:Role
- SpecIF:UserStory SpecIF:isSpecializationOfResource SpecIF:Paragraph
- SpecIF:UserStory SpecIF:hasProperty SpecIF:Priority
- SpecIF:PainPoint SpecIF:isSpecializationOfResource SpecIF:Paragraph
- SpecIF:Namespace SpecIF:hasProperty SpecIF:Term
- SpecIF:Namespace SpecIF:hasProperty dcterms:description
- SpecIF:Namespace SpecIF:hasProperty SpecIF:Origin
- SpecIF:TermPropertyClass SpecIF:hasProperty SpecIF:isRequired
- SpecIF:TermPropertyClass SpecIF:hasProperty SpecIF:multiple
- SpecIF:TermResourceClass SpecIF:hasProperty SpecIF:LocalTermPlural
- SpecIF:TermResourceClass SpecIF:hasProperty SpecIF:Icon
- SpecIF:TermResourceClass SpecIF:hasProperty SpecIF:isHeading
- SpecIF:TermResourceClass SpecIF:hasProperty SpecIF:Instantiation
- SpecIF:TermStatementClass SpecIF:hasProperty SpecIF:Icon
- SpecIF:TermStatementClass SpecIF:hasProperty SpecIF:isUndirected
- SpecIF:TermStatementClass SpecIF:hasProperty SpecIF:Instantiation
- SpecIF:TermPropertyClassString SpecIF:hasProperty SpecIF:singleLanguage
- SpecIF:TermPropertyClassString SpecIF:hasProperty SpecIF:TextFormat
- SpecIF:TermPropertyClassString SpecIF:hasProperty SpecIF:DefaultValueString
- SpecIF:TermPropertyClassString SpecIF:hasProperty SpecIF:StringMaxLength
- SpecIF: SpecIF:isNamespace SpecIF:DefaultValueString
- SpecIF: SpecIF:isNamespace SpecIF:DefaultValue
- SpecIF:TermPropertyClassBoolean SpecIF:hasProperty SpecIF:DefaultValueBoolean
- SpecIF:TermPropertyClassInteger SpecIF:hasProperty SpecIF:DefaultValueInteger
- SpecIF:TermPropertyClassInteger SpecIF:hasProperty SpecIF:Unit
- SpecIF:TermPropertyClassInteger SpecIF:hasProperty SpecIF:IntegerMinInclusive
- SpecIF:TermPropertyClassInteger SpecIF:hasProperty SpecIF:IntegerMaxInclusive
- SpecIF:TermPropertyClassReal SpecIF:hasProperty SpecIF:DefaultValueReal
- SpecIF:TermPropertyClassReal SpecIF:hasProperty SpecIF:Unit
- SpecIF:TermPropertyClassReal SpecIF:hasProperty SpecIF:RealMinInclusive
- SpecIF:TermPropertyClassReal SpecIF:hasProperty SpecIF:RealMaxInclusive
- SpecIF:TermPropertyClassReal SpecIF:hasProperty SpecIF:RealFractionDigits
- SpecIF:TermPropertyClassTimestamp SpecIF:hasProperty SpecIF:DefaultValueTimestamp
- SpecIF: SpecIF:isNamespace SpecIF:TermPropertyClassDuration
- SpecIF:TermPropertyClassDuration SpecIF:hasProperty SpecIF:DefaultValueDuration
- SpecIF:TermPropertyClassURI SpecIF:hasProperty SpecIF:DefaultValueAnyURI
- SpecIF:Paragraph SpecIF:hasProperty SpecIF:Diagram
- SpecIF:Paragraph SpecIF:hasProperty dcterms:type
- SpecIF:Glossary SpecIF:hasProperty dcterms:title
- SpecIF:Glossary SpecIF:hasProperty dcterms:description
- W3C:Ontology SpecIF:hasProperty dcterms:title
- W3C:Ontology SpecIF:hasProperty dcterms:description
- W3C:Ontology SpecIF:hasProperty dcterms:type
- SpecIF:Glossary SpecIF:hasProperty dcterms:type
- SpecIF:isSynonymOfResource SpecIF:isSpecializationOfStatement SpecIF:isSynonymOf
- SpecIF:isSynonymOfStatement SpecIF:isSpecializationOfStatement SpecIF:isSynonymOf
- SpecIF:isSynonymOfProperty SpecIF:isSpecializationOfStatement SpecIF:isSynonymOf
- SpecIF:TermPropertyClassString SpecIF:isEligibleAsSubject SpecIF:isSynonymOfProperty
- SpecIF:TermPropertyClassBoolean SpecIF:isEligibleAsSubject SpecIF:isSynonymOfProperty
- SpecIF:TermPropertyClassInteger SpecIF:isEligibleAsSubject SpecIF:isSynonymOfProperty
- SpecIF:TermPropertyClassReal SpecIF:isEligibleAsSubject SpecIF:isSynonymOfProperty
- SpecIF:TermPropertyClassTimestamp SpecIF:isEligibleAsSubject SpecIF:isSynonymOfProperty
- SpecIF:TermPropertyClassDuration SpecIF:isEligibleAsSubject SpecIF:isSynonymOfProperty
- SpecIF:TermPropertyClassURI SpecIF:isEligibleAsSubject SpecIF:isSynonymOfProperty
- SpecIF:TermPropertyClassString SpecIF:isEligibleAsObject SpecIF:isSynonymOfProperty
- SpecIF:TermPropertyClassBoolean SpecIF:isEligibleAsObject SpecIF:isSynonymOfProperty
- SpecIF:TermPropertyClassInteger SpecIF:isEligibleAsObject SpecIF:isSynonymOfProperty
- SpecIF:TermPropertyClassReal SpecIF:isEligibleAsObject SpecIF:isSynonymOfProperty
- SpecIF:TermPropertyClassTimestamp SpecIF:isEligibleAsObject SpecIF:isSynonymOfProperty
- SpecIF:TermPropertyClassDuration SpecIF:isEligibleAsObject SpecIF:isSynonymOfProperty
- SpecIF:TermPropertyClassURI SpecIF:isEligibleAsObject SpecIF:isSynonymOfProperty
- SpecIF:TermStatementClass SpecIF:isEligibleAsSubject SpecIF:isSynonymOfStatement
- SpecIF:TermStatementClass SpecIF:isEligibleAsObject SpecIF:isSynonymOfStatement
- SpecIF:TermResourceClass SpecIF:isEligibleAsSubject SpecIF:isSynonymOfResource
- SpecIF:TermResourceClass SpecIF:isEligibleAsObject SpecIF:isSynonymOfResource
- SpecIF:isSynonymOfValue SpecIF:isSpecializationOfStatement SpecIF:isSynonymOf
- SpecIF:TermPropertyValue SpecIF:isEligibleAsSubject SpecIF:isSynonymOfValue
- SpecIF:TermPropertyValue SpecIF:isEligibleAsObject SpecIF:isSynonymOfValue
- SpecIF: SpecIF:isNamespace SpecIF:isAntonymOfValue
- SpecIF:isAntonymOfValue SpecIF:isSpecializationOfStatement SpecIF:isAntonymOf
- SpecIF:TermPropertyValue SpecIF:isEligibleAsSubject SpecIF:isAntonymOfValue
- SpecIF:TermPropertyValue SpecIF:isEligibleAsObject SpecIF:isAntonymOfValue
- SpecIF: SpecIF:isNamespace SpecIF:isPluralOfResource
- SpecIF:isPluralOfResource SpecIF:isSpecializationOfStatement SpecIF:isPluralOf
- SpecIF:TermResourceClass SpecIF:isEligibleAsSubject SpecIF:isPluralOfResource
- SpecIF:TermResourceClass SpecIF:isEligibleAsObject SpecIF:isPluralOfResource
- SpecIF:TermResourceClass SpecIF:isEligibleAsSubject SpecIF:isSpecializationOfResource
- SpecIF:TermResourceClass SpecIF:isEligibleAsObject SpecIF:isSpecializationOfResource
- SpecIF: SpecIF:isNamespace SpecIF:isEligibleAsSubject
- SpecIF:TermResourceClass SpecIF:isEligibleAsSubject SpecIF:isEligibleAsSubject
- SpecIF:TermStatementClass SpecIF:isEligibleAsSubject SpecIF:isEligibleAsSubject
- SpecIF:TermStatementClass SpecIF:isEligibleAsObject SpecIF:isEligibleAsSubject
- SpecIF: SpecIF:isNamespace SpecIF:isSpecializationOfResource
- SpecIF:TermStatementClass SpecIF:isEligibleAsSubject SpecIF:isSpecializationOfStatement
- SpecIF:TermStatementClass SpecIF:isEligibleAsObject SpecIF:isSpecializationOfStatement
- SpecIF: SpecIF:isNamespace SpecIF:isSpecializationOfStatement
- SpecIF:isGeneralizationOfResource SpecIF:isSpecializationOfStatement uml:Generalization
- SpecIF:TermResourceClass SpecIF:isEligibleAsSubject SpecIF:isGeneralizationOfResource
- SpecIF:TermResourceClass SpecIF:isEligibleAsObject SpecIF:isGeneralizationOfResource
- SpecIF: SpecIF:isNamespace SpecIF:isGeneralizationOfResource
- SpecIF:isGeneralizationOfStatement SpecIF:isSpecializationOfStatement uml:Generalization
- SpecIF:TermStatementClass SpecIF:isEligibleAsSubject SpecIF:isGeneralizationOfStatement
- SpecIF:TermStatementClass SpecIF:isEligibleAsObject SpecIF:isGeneralizationOfStatement
- SpecIF: SpecIF:isNamespace SpecIF:isGeneralizationOfStatement
- SpecIF:TermResourceClass SpecIF:isEligibleAsSubject SpecIF:isEligibleAsObject
- SpecIF:TermStatementClass SpecIF:isEligibleAsSubject SpecIF:isEligibleAsObject
- SpecIF:TermStatementClass SpecIF:isEligibleAsObject SpecIF:isEligibleAsObject
- SpecIF: SpecIF:isNamespace SpecIF:isEligibleAsObject
- SpecIF:TermPropertyClassInteger SpecIF:isEligibleAsSubject SpecIF:hasEnumValue
- SpecIF:TermPropertyClassReal SpecIF:isEligibleAsSubject SpecIF:hasEnumValue
- SpecIF:TermPropertyClassDuration SpecIF:isEligibleAsSubject SpecIF:hasEnumValue
- SpecIF:TermPropertyClassTimestamp SpecIF:isEligibleAsSubject SpecIF:hasEnumValue
- SpecIF:TermPropertyClassURI SpecIF:isEligibleAsSubject SpecIF:hasEnumValue
- SpecIF:hasEnumValue SpecIF:hasProperty SpecIF:Index
- SpecIF:hasProperty SpecIF:hasProperty SpecIF:Index
- SpecIF:TermResourceClass SpecIF:isEligibleAsSubject SpecIF:hasProperty
- SpecIF:TermStatementClass SpecIF:isEligibleAsSubject SpecIF:hasProperty
- SpecIF:TermPropertyClassString SpecIF:isEligibleAsObject SpecIF:hasProperty
- SpecIF:TermPropertyClassBoolean SpecIF:isEligibleAsObject SpecIF:hasProperty
- SpecIF:TermPropertyClassInteger SpecIF:isEligibleAsObject SpecIF:hasProperty
- SpecIF:TermPropertyClassReal SpecIF:isEligibleAsObject SpecIF:hasProperty
- SpecIF:TermPropertyClassDuration SpecIF:isEligibleAsObject SpecIF:hasProperty
- SpecIF:TermPropertyClassTimestamp SpecIF:isEligibleAsObject SpecIF:hasProperty
- SpecIF:TermPropertyClassURI SpecIF:isEligibleAsObject SpecIF:hasProperty
- SpecIF:isEligibleAsSubject SpecIF:hasProperty SpecIF:Index
- SpecIF:isEligibleAsObject SpecIF:hasProperty SpecIF:Index
- SpecIF:Namespace SpecIF:isEligibleAsSubject SpecIF:isNamespace
- SpecIF:TermResourceClass SpecIF:isEligibleAsObject SpecIF:isNamespace
- SpecIF:TermStatementClass SpecIF:isEligibleAsObject SpecIF:isNamespace
- SpecIF:TermPropertyClassString SpecIF:isEligibleAsObject SpecIF:isNamespace
- SpecIF:TermPropertyClassBoolean SpecIF:isEligibleAsObject SpecIF:isNamespace
- SpecIF:TermPropertyClassInteger SpecIF:isEligibleAsObject SpecIF:isNamespace
- SpecIF:TermPropertyClassReal SpecIF:isEligibleAsObject SpecIF:isNamespace
- SpecIF:TermPropertyClassDuration SpecIF:isEligibleAsObject SpecIF:isNamespace
- SpecIF:TermPropertyClassTimestamp SpecIF:isEligibleAsObject SpecIF:isNamespace
- SpecIF:TermPropertyClassURI SpecIF:isEligibleAsObject SpecIF:isNamespace
- SpecIF:TermPropertyValue SpecIF:isEligibleAsObject SpecIF:isNamespace
- SpecIF:Issue SpecIF:isEligibleAsSubject SpecIF:issueRefersTo
- SpecIF:TermStatus SpecIF:hasEnumValue SpecIF:LifecycleStatusReleased
- SpecIF:TermStatus SpecIF:hasEnumValue SpecIF:LifecycleStatusEquivalent
- SpecIF:TermStatus SpecIF:hasEnumValue SpecIF:LifecycleStatusDeprecated
- SpecIF:Domain SpecIF:hasEnumValue SpecIF:DomainBase
- SpecIF:Domain SpecIF:hasEnumValue SpecIF:DomainRequirementsEngineering
- SpecIF:Domain SpecIF:hasEnumValue SpecIF:DomainRequirementsEngineeringSRC
- SpecIF:Domain SpecIF:hasEnumValue SpecIF:DomainSystemsEngineering
- SpecIF:Domain SpecIF:hasEnumValue SpecIF:DomainSystemTesting
- SpecIF:Domain SpecIF:hasEnumValue SpecIF:DomainSystemModelIntegration
- SpecIF:Domain SpecIF:hasEnumValue SpecIF:DomainVariantManagement
- SpecIF:Domain SpecIF:hasEnumValue SpecIF:DomainIssueManagement
- SpecIF:Domain SpecIF:hasEnumValue SpecIF:DomainAgileSystemDevelopment
- SpecIF:Domain SpecIF:hasEnumValue SpecIF:DomainProductLifecycleManagement
- SpecIF:Domain SpecIF:hasEnumValue SpecIF:DomainOntology
- SpecIF:Domain SpecIF:hasEnumValue SpecIF:DomainOther
- SpecIF:Instantiation SpecIF:hasEnumValue SpecIF:InstantiationAuto
- SpecIF:Instantiation SpecIF:hasEnumValue SpecIF:InstantiationUser
- SpecIF: SpecIF:isNamespace SpecIF:TextFormat
- SpecIF:TextFormat SpecIF:hasEnumValue SpecIF:TextFormatPlain
- SpecIF:TextFormat SpecIF:hasEnumValue SpecIF:TextFormatXhtml
- SpecIF: SpecIF:isNamespace SpecIF:isAntonymOfStatement
- SpecIF:isAntonymOfStatement SpecIF:isSpecializationOfStatement SpecIF:isAntonymOf
- SpecIF:TermStatementClass SpecIF:isEligibleAsSubject SpecIF:isAntonymOfStatement
- SpecIF:TermStatementClass SpecIF:isEligibleAsObject SpecIF:isAntonymOfStatement
- SpecIF: SpecIF:isNamespace SpecIF:isSynonymOfValue
- SpecIF: SpecIF:isNamespace SpecIF:isSynonymOfProperty
- SpecIF: SpecIF:isNamespace SpecIF:isSynonymOfStatement
- SpecIF: SpecIF:isNamespace SpecIF:isSynonymOfResource
- SpecIF: SpecIF:isNamespace SpecIF:isSynonymOf
- rdfs: SpecIF:isNamespace rdfs:comment
- rdfs:comment SpecIF:isSynonymOfProperty dcterms:description
- rdfs: SpecIF:isNamespace rdfs:label
- rdfs:label SpecIF:isSynonymOfProperty dcterms:title
- IR:Annotation SpecIF:hasProperty dcterms:description
- IR:Annotation SpecIF:isSynonymOfResource SpecIF:Comment
- SpecIF: SpecIF:isNamespace SpecIF:Permissions
- SpecIF:Permissions SpecIF:hasProperty dcterms:title
- SpecIF:Views SpecIF:hasProperty SpecIF:LocalTerm
- SpecIF: SpecIF:isNamespace SpecIF:Issue
- SpecIF:Issue SpecIF:hasProperty dcterms:title
- SpecIF:Issue SpecIF:hasProperty dcterms:description
- SpecIF:Issue SpecIF:hasProperty oslc_cm:Severity
- SpecIF:Issue SpecIF:hasProperty oslc_cm:Status
- SpecIF: SpecIF:isNamespace SpecIF:UnreferencedResources
- SpecIF:UnreferencedResources SpecIF:hasProperty dcterms:title
- SpecIF:UnreferencedResources SpecIF:hasProperty dcterms:description
- uml: SpecIF:isNamespace uml:Package
- uml:Package SpecIF:hasProperty dcterms:title
- uml:Package SpecIF:hasProperty dcterms:description
- SpecIF:isSpecializationOfResource SpecIF:isSpecializationOfStatement SpecIF:isSpecializationOf
- SpecIF:isSpecializationOfStatement SpecIF:isSpecializationOfStatement SpecIF:isSpecializationOf
- FMC:contains SpecIF:isSynonymOfStatement dcterms:hasPart
- ArchiMate:Uniting SpecIF:isSynonymOfStatement dcterms:hasPart
- FMC:Actor SpecIF:isEligibleAsSubject dcterms:hasPart
- FMC:State SpecIF:isEligibleAsSubject dcterms:hasPart
- SpecIF:Collection SpecIF:isEligibleAsSubject dcterms:hasPart
- FMC:Actor SpecIF:isEligibleAsObject dcterms:hasPart
- FMC:State SpecIF:isEligibleAsObject dcterms:hasPart
- SpecIF:Collection SpecIF:isEligibleAsObject dcterms:hasPart
- SpecIF:ModelElement SpecIF:isEligibleAsObject dcterms:hasPart
- oslc_rm:decomposes SpecIF:isSynonymOfStatement dcterms:isPartOf
- uml:Package SpecIF:isSpecializationOfResource SpecIF:Collection
- uml:Association SpecIF:hasProperty dcterms:type
- uml:Aggregation SpecIF:hasProperty dcterms:type
- SpecIF:relates SpecIF:hasProperty dcterms:type
- dcterms:hasPart SpecIF:isSpecializationOfStatement SpecIF:relates
- uml:Aggregation SpecIF:isSpecializationOfStatement SpecIF:relates
- uml:Composition SpecIF:isSpecializationOfStatement SpecIF:relates
- uml:Association SpecIF:isSpecializationOfStatement SpecIF:relates
- uml:Generalization SpecIF:isSpecializationOfStatement SpecIF:relates
- SpecIF:Reader SpecIF:isSpecializationOfResource SpecIF:UserRole
- SpecIF:Editor SpecIF:isSpecializationOfResource SpecIF:UserRole
- ReqIF-WF.Customer SpecIF:isSpecializationOfResource SpecIF:UserRole
- ReqIF-WF.Supplier SpecIF:isSpecializationOfResource SpecIF:UserRole
- SpecIF: SpecIF:isNamespace SpecIF:Reader
- sysml: SpecIF:isNamespace sysml:Refine
- sysml:Refine SpecIF:isSynonymOfStatement IREB:refines
- sysml: SpecIF:isNamespace sysml:Satisfy
- sysml:Satisfy SpecIF:isSynonymOfStatement oslc_rm:satisfies
- ArchiMate:Assignment SpecIF:isSynonymOfStatement sysml:Allocate
- SpecIF:realizedBy SpecIF:isSynonymOfStatement sysml:Allocate
- SpecIF:ModelElement SpecIF:isEligibleAsSubject sysml:Allocate
- SpecIF:ModelElement SpecIF:isEligibleAsObject sysml:Allocate
- sysml: SpecIF:isNamespace sysml:Allocate
- uml:Package SpecIF:isEligibleAsSubject SpecIF:contains
- uml:Package SpecIF:isEligibleAsObject SpecIF:contains
- SpecIF:ModelElement SpecIF:isEligibleAsObject SpecIF:contains
- SpecIF:View SpecIF:isEligibleAsObject SpecIF:contains
- SpecIF:ModelElement SpecIF:isEligibleAsSubject dcterms:hasPart
- uml: SpecIF:isNamespace uml:is_Service
- uml: SpecIF:isNamespace uml:Flow_Direction
- uml: SpecIF:isNamespace uml:Stereotype
- uml: SpecIF:isNamespace uml:Port
- uml:Port SpecIF:isSpecializationOfResource FMC:Actor
- uml:Port SpecIF:hasProperty uml:is_Service
- uml:Port SpecIF:hasProperty uml:Flow_Direction
- uml:Port SpecIF:isEligibleAsObject dcterms:hasPart
- uml:Port SpecIF:isEligibleAsSubject SpecIF:reads
- uml:Port SpecIF:isEligibleAsSubject SpecIF:writes
- uml:Port SpecIF:isEligibleAsSubject SpecIF:accesses
- SpecIF: SpecIF:isNamespace SpecIF:provides
- FMC:Actor SpecIF:isEligibleAsSubject SpecIF:provides
- uml:Port SpecIF:isEligibleAsSubject SpecIF:provides
- FMC:State SpecIF:isEligibleAsObject SpecIF:provides
- SpecIF: SpecIF:isNamespace SpecIF:consumes
- FMC:Actor SpecIF:isEligibleAsSubject SpecIF:consumes
- uml:Port SpecIF:isEligibleAsSubject SpecIF:consumes
- FMC:State SpecIF:isEligibleAsObject SpecIF:consumes
- SpecIF: SpecIF:isNamespace SpecIF:handles
- SpecIF:consumes SpecIF:isSpecializationOfStatement SpecIF:handles
- SpecIF:provides SpecIF:isSpecializationOfStatement SpecIF:handles
- FMC:Actor SpecIF:isEligibleAsSubject SpecIF:handles
- FMC:State SpecIF:isEligibleAsObject SpecIF:handles
- uml:Port SpecIF:isEligibleAsSubject SpecIF:handles
- uml:Port SpecIF:isEligibleAsSubject FMC:communicatesWith
- uml:Port SpecIF:isEligibleAsObject FMC:communicatesWith
- uml:Port SpecIF:isEligibleAsSubject SpecIF:serves
- uml:Port SpecIF:isEligibleAsObject SpecIF:serves
- ArchiMate:Serving SpecIF:isSynonymOfStatement SpecIF:serves
- FMC: SpecIF:isNamespace FMC:requests
- FMC:requests SpecIF:isAntonymOfStatement SpecIF:serves
- SpecIF: SpecIF:isNamespace SpecIF:isAssociatedWith
- SpecIF:isAssociatedWith SpecIF:isSpecializationOfStatement SpecIF:relates
- uml:Composition SpecIF:isSynonymOfStatement dcterms:hasPart
- SpecIF: SpecIF:isNamespace SpecIF:aggregates
- uml:Aggregation SpecIF:isSynonymOfStatement SpecIF:aggregates
- SpecIF:aggregates SpecIF:isSpecializationOfStatement SpecIF:relates
- uml:Association SpecIF:isSynonymOfStatement SpecIF:isAssociatedWith
- uml:Generalization SpecIF:isAntonymOfStatement SpecIF:isSpecializationOf
- SpecIF:inheritsFrom SpecIF:isSynonymOfStatement SpecIF:isSpecializationOf
- IR:inheritsFrom SpecIF:isSynonymOfStatement SpecIF:isSpecializationOf
- ArchiMate:DataObject SpecIF:isSpecializationOfResource FMC:State
- ArchiMate: SpecIF:isNamespace ArchiMate:BusinessObject
- ArchiMate:BusinessObject SpecIF:isSpecializationOfResource FMC:State
- ArchiMate: SpecIF:isNamespace ArchiMate:DataObject
- ArchiMate: SpecIF:isNamespace ArchiMate:ApplicationComponent
- ArchiMate:ApplicationComponent SpecIF:isSpecializationOfResource FMC:Actor
- bpmn:processStep SpecIF:isSpecializationOfResource FMC:Actor
- bpmn: SpecIF:isNamespace bpmn:dataStore
- bpmn:dataStore SpecIF:isSpecializationOfResource FMC:State
- bpmn:startEvent SpecIF:isSpecializationOfResource FMC:Event
- bpmn:intermediateEvent SpecIF:isSpecializationOfResource FMC:Event
- bpmn:endEvent SpecIF:isSpecializationOfResource FMC:Event
- bpmn: SpecIF:isNamespace bpmn:dataObject
- bpmn:dataObject SpecIF:isSpecializationOfResource FMC:State
- SpecIF:ModelElement SpecIF:isEligibleAsSubject SpecIF:consumes
- SpecIF:ModelElement SpecIF:isEligibleAsObject SpecIF:consumes
- SpecIF:ModelElement SpecIF:isEligibleAsSubject SpecIF:provides
- SpecIF:ModelElement SpecIF:isEligibleAsObject SpecIF:provides
- SpecIF:ModelElement SpecIF:isEligibleAsSubject SpecIF:handles
- SpecIF:ModelElement SpecIF:isEligibleAsObject SpecIF:handles
- xs: SpecIF:isNamespace xs:string
- uml:Class SpecIF:isSynonymOfResource SpecIF:ModelElement
- uml: SpecIF:isNamespace uml:Class_Diagram
- uml: SpecIF:isNamespace uml:Activity_Diagram
- FMC: SpecIF:isNamespace FMC:Entity-Relationship_Diagram
- FMC: SpecIF:isNamespace FMC:Petri_Net
- FMC: SpecIF:isNamespace FMC:Block_Diagram
- uml:Diagram SpecIF:isSynonymOfResource SpecIF:View
- uml: SpecIF:isNamespace uml:Diagram
- uml:Diagram SpecIF:isSpecializationOfResource SpecIF:Paragraph
- uml:Class SpecIF:isEligibleAsSubject dcterms:hasPart
- uml:Class SpecIF:isEligibleAsObject dcterms:hasPart
- ArchiMate:Composition SpecIF:isSpecializationOfStatement ArchiMate:Uniting
- SpecIF: SpecIF:isNamespace SpecIF:isResponsibilityOf
- SpecIF:isResponsibilityOf SpecIF:isAntonymOfStatement SpecIF:isResponsibleFor
- SpecIF: SpecIF:isNamespace SpecIF:isResponsibleFor
- ArchiMate:Assignment SpecIF:isSynonymOfStatement SpecIF:isResponsibleFor
- SpecIF: SpecIF:isNamespace SpecIF:impliedBy
- SpecIF:impliedBy SpecIF:isAntonymOfStatement SpecIF:implies
- SpecIF: SpecIF:isNamespace SpecIF:implies
- IREB:Requirement SpecIF:isEligibleAsObject SpecIF:implies
- SpecIF:DesignDecision SpecIF:isEligibleAsObject SpecIF:implies
- IREB:Requirement SpecIF:isEligibleAsSubject SpecIF:impliedBy
- SpecIF:DesignDecision SpecIF:isEligibleAsSubject SpecIF:impliedBy
- SpecIF:realizedBy SpecIF:isAntonymOfStatement SpecIF:realizes
- SpecIF:realizes SpecIF:isSynonymOfStatement ArchiMate:Realization
- bpmn: SpecIF:isNamespace bpmn:dataInputAssociation
- bpmn: SpecIF:isNamespace bpmn:dataOutputAssociation
- bpmn:dataOutputAssociation SpecIF:isSynonymOfStatement SpecIF:writes
- bpmn:dataInputAssociation SpecIF:isSynonymOfStatement SpecIF:reads
- SpecIF:Outline SpecIF:isSpecializationOfResource SpecIF:Hierarchy
- SpecIF:BillOfMaterials SpecIF:isSpecializationOfResource SpecIF:Hierarchy
- SpecIF:Glossary SpecIF:isSpecializationOfResource SpecIF:Hierarchy
- SpecIF:UnreferencedResources SpecIF:isSpecializationOfResource SpecIF:Hierarchy
- SpecIF:Views SpecIF:isSpecializationOfResource SpecIF:Hierarchy
- SpecIF:Object SpecIF:isSynonymOfProperty SpecIF:hasObject
- SpecIF:Subject SpecIF:isSynonymOfProperty SpecIF:hasSubject
- SpecIF:HierarchyRoot SpecIF:hasProperty dcterms:title
- SpecIF:HierarchyRoot SpecIF:hasProperty dcterms:description
- SpecIF:hasItem SpecIF:isSpecializationOfStatement dcterms:hasPart
- FMC:Actor SpecIF:isSpecializationOfResource SpecIF:ModelElement
- FMC:State SpecIF:isSpecializationOfResource SpecIF:ModelElement
- FMC:Event SpecIF:isSpecializationOfResource SpecIF:ModelElement
- uml:Class SpecIF:isSpecializationOfResource SpecIF:ModelElement
- SpecIF:Collection SpecIF:isSpecializationOfResource SpecIF:ModelElement
- uml:StateMachine SpecIF:isSpecializationOfResource FMC:Actor
- uml:Region SpecIF:isSpecializationOfResource FMC:Actor
- uml: SpecIF:isNamespace uml:Region
- uml: SpecIF:isNamespace uml:StateMachine
- uml: SpecIF:isNamespace uml:State
- uml:State SpecIF:isSpecializationOfResource FMC:State
- uml: SpecIF:isNamespace uml:Transition
- uml:Transition SpecIF:isSpecializationOfResource FMC:Actor
- uml: SpecIF:isNamespace uml:ownedBehavior
- uml:StateMachine SpecIF:isEligibleAsObject uml:ownedBehavior
- uml: SpecIF:isNamespace uml:Activity
- uml:Activity SpecIF:isSpecializationOfResource FMC:Actor
- uml:Activity SpecIF:isEligibleAsObject uml:ownedBehavior
- FMC:Actor SpecIF:isEligibleAsObject uml:ownedBehavior
- uml: SpecIF:isNamespace uml:Trigger
- uml: SpecIF:isNamespace uml:ChangeEvent
- uml:ChangeEvent SpecIF:isSpecializationOfResource FMC:Event
- uml: SpecIF:isNamespace uml:CallEvent
- uml:CallEvent SpecIF:isSpecializationOfResource FMC:Event
- uml: SpecIF:isNamespace uml:SignalEvent
- uml:SignalEvent SpecIF:isSpecializationOfResource FMC:Event
- uml: SpecIF:isNamespace uml:TransitionTarget
- uml:Transition SpecIF:isEligibleAsSubject uml:TransitionTarget
- FMC:Actor SpecIF:isEligibleAsSubject uml:TransitionTarget
- uml:State SpecIF:isEligibleAsObject uml:TransitionTarget
- FMC:State SpecIF:isEligibleAsObject uml:TransitionTarget
- uml: SpecIF:isNamespace uml:TransitionSource
- uml:Transition SpecIF:isEligibleAsSubject uml:TransitionSource
- FMC:Actor SpecIF:isEligibleAsSubject uml:TransitionSource
- uml:State SpecIF:isEligibleAsObject uml:TransitionSource
- FMC:State SpecIF:isEligibleAsObject uml:TransitionSource
- uml: SpecIF:isNamespace uml:ControlFlow
- FMC:Actor SpecIF:isEligibleAsSubject uml:ControlFlow
- FMC:Actor SpecIF:isEligibleAsObject uml:ControlFlow
- uml:ControlFlow SpecIF:isSynonymOfStatement SpecIF:precedes
- uml: SpecIF:isNamespace uml:CallBehaviorAction
- uml:CallBehaviorAction SpecIF:isSpecializationOfResource FMC:Actor
- uml: SpecIF:isNamespace uml:InitialNode
- uml:InitialNode SpecIF:isSpecializationOfResource FMC:Actor
- uml: SpecIF:isNamespace uml:ActivityFinalNode
- uml:ActivityFinalNode SpecIF:isSpecializationOfResource FMC:Actor
- sysml: SpecIF:isNamespace sysml:Requirement
- sysml:Requirement SpecIF:isSynonymOfResource IREB:Requirement
- SpecIF:Requirement SpecIF:isSpecializationOfResource IREB:Requirement
- sysml:Requirement SpecIF:isSpecializationOfResource IREB:Requirement

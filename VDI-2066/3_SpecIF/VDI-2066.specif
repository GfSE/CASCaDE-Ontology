# VDI-2066
A set of SpecIF Classes derived from a SpecIF Ontology for the domains SpecIF:DomainBase, SpecIF:DomainSystemsEngineering, SpecIF:DomainSystemModelIntegration.
- Rights: Creative Commons 4.0 CC BY-SA, https://creativecommons.org/licenses/by-sa/4.0/

## VDI-2066 (SpecIF:Heading)
- dcterms:type: uml:Model

## Mechatronic_System_Environment (SpecIF:View)
- SpecIF:Diagram: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
- dcterms:type: uml:Diagram
- SpecIF:Notation: SysML Block Definition Diagram

## Environment (SpecIF:ModelElement)
- dcterms:type: sysml:Block

## Human (SpecIF:ModelElement)
- dcterms:type: sysml:Block

## Communication_System (SpecIF:ModelElement)
- dcterms:type: sysml:Block

## Information (FMC:State)
- dcterms:type: uml:Class

## Sensor_Information (FMC:State)
- dcterms:type: uml:Class

## Actuator_Information (FMC:State)
- dcterms:type: uml:Class

## Energy (FMC:State)
- dcterms:type: uml:Class
- dcterms:description: The energy flow in and out of the system, here in its most general form. Should be specialized to its actual form in an application, such as electrical, mechanical or other energy.

  Definition: In physics, power is the amount of energy transferred or converted per unit time. In the International System of Units, the unit of power is the watt, equal to one joule per second. Power is a scalar quantity. Power is the rate with respect to time at which work is done; it is the time derivative of work. Source: [Wikipedia](https://en.wikipedia.org/wiki/Power_(physics)).

## Electrical_Energy (FMC:State)
- dcterms:type: uml:Class

## power (SpecIF:ModelElement)
- dcterms:type: uml:DataType

## Material (FMC:State)
- dcterms:type: uml:Class

## Water (FMC:State)
- dcterms:type: uml:Class

## Mechatronic_System_Design_Process (SpecIF:View)
- SpecIF:Diagram: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
- dcterms:type: uml:Diagram
- SpecIF:Notation: SysML Block Definition Diagram

## Requirement (SpecIF:ModelElement)
- dcterms:type: sysml:Block

## requirement (SpecIF:ModelElement)
- dcterms:type: uml:Class

## Function (SpecIF:ModelElement)
- dcterms:type: sysml:Block

## function (SpecIF:ModelElement)
- dcterms:type: uml:Class

## System (SpecIF:ModelElement)
- dcterms:type: sysml:Block

## system (SpecIF:ModelElement)
- dcterms:type: uml:Class

## Simple_Mechatronic_System (SpecIF:ModelElement)
- dcterms:type: sysml:Block

## Programmable_Mechatronic_System (SpecIF:ModelElement)
- dcterms:type: sysml:Block

## Cyber-Physical_System (SpecIF:ModelElement)
- dcterms:type: sysml:Block

## Mechatronic_System (SpecIF:ModelElement)
- dcterms:type: sysml:Block
- dcterms:description: Disturbances from the Environment are neglected, here

## Mechatronic_System (SpecIF:View)
- SpecIF:Diagram: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
- dcterms:type: uml:Diagram
- SpecIF:Notation: SysML Internal Block Diagram

## Information_Processing (SpecIF:ModelElement)
- dcterms:type: sysml:Block

## informationProcessing (SpecIF:ModelElement)
- dcterms:type: uml:Class

## Actuator (SpecIF:ModelElement)
- dcterms:type: sysml:Block

## actuator (SpecIF:ModelElement)
- dcterms:type: uml:Class

## Sensor (SpecIF:ModelElement)
- dcterms:type: sysml:Block

## sensor (SpecIF:ModelElement)
- dcterms:type: uml:Class

## Basic_System (SpecIF:ModelElement)
- dcterms:type: sysml:Block

## basicSystem (SpecIF:ModelElement)
- dcterms:type: uml:Class

## Unit Imports (uml:Package)
- dcterms:type: uml:Package

## Basic Unit Categories (SpecIF:View)
- dcterms:type: uml:Diagram
- SpecIF:Notation: UML Dependency Matrix

## Basic Units (SpecIF:View)
- dcterms:type: uml:Diagram
- SpecIF:Notation: UML Dependency Matrix

## Basic Units (uml:Package)
- dcterms:type: uml:Package

## Basic Length (uml:Package)
- dcterms:type: uml:Package

## Basic Mass (uml:Package)
- dcterms:type: uml:Package

## Basic Area (uml:Package)
- dcterms:type: uml:Package

## Basic Volume (uml:Package)
- dcterms:type: uml:Package

## Basic Time (uml:Package)
- dcterms:type: uml:Package

## Basic Electric Current (uml:Package)
- dcterms:type: uml:Package

## Basic Thermodynamic Temperature (uml:Package)
- dcterms:type: uml:Package

## Basic Amount of Substance (uml:Package)
- dcterms:type: uml:Package

## Basic Luminous Intensity (uml:Package)
- dcterms:type: uml:Package

## Basic Speed and Velocity (uml:Package)
- dcterms:type: uml:Package

## Basic Acceleration (uml:Package)
- dcterms:type: uml:Package

## Basic Mass Density (uml:Package)
- dcterms:type: uml:Package

## Basic Electric Current Density (uml:Package)
- dcterms:type: uml:Package

## Basic Amount of Substance Concentration (uml:Package)
- dcterms:type: uml:Package

## Basic Magnetic Field Strength (uml:Package)
- dcterms:type: uml:Package

## Basic Luminance (uml:Package)
- dcterms:type: uml:Package

## Model Elements (Glossary) (SpecIF:Heading)
- dcterms:type: SpecIF:Glossary

## Actuator Port actuator-control-in (uml:Port)
- dcterms:type: uml:Port
- uml:is_Service: true
- uml:Flow_Direction: in

## Actuator Port actuator-energy-out (uml:Port)
- dcterms:type: uml:Port
- uml:is_Service: true
- uml:Flow_Direction: out

## Actuator Port energy-in (uml:Port)
- dcterms:type: uml:Port
- uml:is_Service: false
- uml:Flow_Direction: in

## Basic_System Port actuator-energy-in (uml:Port)
- dcterms:type: uml:Port
- uml:is_Service: false
- uml:Flow_Direction: in

## Basic_System Port energy-in (uml:Port)
- dcterms:type: uml:Port
- uml:is_Service: false
- uml:Flow_Direction: in

## Basic_System Port energy-out (uml:Port)
- dcterms:type: uml:Port
- uml:is_Service: true
- uml:Flow_Direction: out

## Basic_System Port material-in (uml:Port)
- dcterms:type: uml:Port
- uml:is_Service: false
- uml:Flow_Direction: in

## Basic_System Port material-out (uml:Port)
- dcterms:type: uml:Port
- uml:is_Service: true
- uml:Flow_Direction: out

## Basic_System Port observed-value (uml:Port)
- dcterms:type: uml:Port
- uml:is_Service: true
- uml:Flow_Direction: out

## Communication_System Port energy-in (uml:Port)
- dcterms:type: uml:Port
- uml:is_Service: true
- uml:Flow_Direction: in

## Communication_System Port information-client (uml:Port)
- dcterms:type: uml:Port
- uml:is_Service: false
- uml:Flow_Direction: inout

## Communication_System Port information-server (uml:Port)
- dcterms:type: uml:Port
- uml:is_Service: true
- uml:Flow_Direction: inout

## Environment Port energy-in (uml:Port)
- dcterms:type: uml:Port
- uml:is_Service: false
- uml:Flow_Direction: in

## Environment Port energy-out (uml:Port)
- dcterms:type: uml:Port
- uml:is_Service: true
- uml:Flow_Direction: out

## Environment Port material-in (uml:Port)
- dcterms:type: uml:Port
- uml:is_Service: false
- uml:Flow_Direction: in

## Environment Port material-out (uml:Port)
- dcterms:type: uml:Port
- uml:is_Service: true
- uml:Flow_Direction: out

## Human Port human-machine-interface-client (uml:Port)
- dcterms:type: uml:Port
- uml:is_Service: false
- uml:Flow_Direction: inout

## Information_Processing Port actuator-control-out (uml:Port)
- dcterms:type: uml:Port
- uml:is_Service: false
- uml:Flow_Direction: out

## Information_Processing Port energy-in (uml:Port)
- dcterms:type: uml:Port
- uml:is_Service: true
- uml:Flow_Direction: in

## Information_Processing Port human-machine-interface-server (uml:Port)
- dcterms:type: uml:Port
- uml:is_Service: true
- uml:Flow_Direction: inout

## Information_Processing Port information-client (uml:Port)
- dcterms:type: uml:Port
- uml:is_Service: true
- uml:Flow_Direction: inout

## Information_Processing Port information-server (uml:Port)
- dcterms:type: uml:Port
- uml:is_Service: true
- uml:Flow_Direction: inout

## Information_Processing Port sensor-reading-in (uml:Port)
- dcterms:type: uml:Port
- uml:is_Service: true
- uml:Flow_Direction: in

## Mechatronic_System Port energy-in (uml:Port)
- dcterms:type: uml:Port
- uml:is_Service: false
- uml:Flow_Direction: in

## Mechatronic_System Port energy-out (uml:Port)
- dcterms:type: uml:Port
- uml:is_Service: true
- uml:Flow_Direction: out

## Mechatronic_System Port human-machine-interface-server (uml:Port)
- dcterms:type: uml:Port
- uml:is_Service: true
- uml:Flow_Direction: inout

## Mechatronic_System Port information-client (uml:Port)
- dcterms:type: uml:Port
- uml:is_Service: false
- uml:Flow_Direction: inout

## Mechatronic_System Port information-server (uml:Port)
- dcterms:type: uml:Port
- uml:is_Service: true
- uml:Flow_Direction: inout

## Mechatronic_System Port material-in (uml:Port)
- dcterms:type: uml:Port
- uml:is_Service: false
- uml:Flow_Direction: in

## Mechatronic_System Port material-out (uml:Port)
- dcterms:type: uml:Port
- uml:is_Service: true
- uml:Flow_Direction: out

## Sensor Port energy-in (uml:Port)
- dcterms:type: uml:Port
- uml:is_Service: true
- uml:Flow_Direction: in

## Sensor Port sensed-value (uml:Port)
- dcterms:type: uml:Port
- uml:is_Service: false
- uml:Flow_Direction: in

## Sensor Port sensor-reading-out (uml:Port)
- dcterms:type: uml:Port
- uml:is_Service: true
- uml:Flow_Direction: out

## Statements
- Unit Imports SpecIF:contains Basic Unit Categories
- Unit Imports SpecIF:contains Basic Units
- Mechatronic_System dcterms:hasPart Mechatronic_System Port material-out
- Mechatronic_System dcterms:hasPart Mechatronic_System Port material-in
- Mechatronic_System dcterms:hasPart Mechatronic_System Port energy-out
- Mechatronic_System dcterms:hasPart Mechatronic_System Port energy-in
- Mechatronic_System dcterms:hasPart Mechatronic_System Port information-client
- Mechatronic_System dcterms:hasPart Mechatronic_System Port information-server
- Mechatronic_System dcterms:hasPart Mechatronic_System Port human-machine-interface-server
- Energy SpecIF:isAssociatedWith power
- Basic_System dcterms:hasPart Basic_System Port material-in
- Basic_System dcterms:hasPart Basic_System Port material-out
- Basic_System dcterms:hasPart Basic_System Port energy-out
- Basic_System dcterms:hasPart Basic_System Port energy-in
- Basic_System dcterms:hasPart Basic_System Port observed-value
- Basic_System dcterms:hasPart Basic_System Port actuator-energy-in
- Sensor dcterms:hasPart Sensor Port sensor-reading-out
- Sensor dcterms:hasPart Sensor Port sensed-value
- Sensor dcterms:hasPart Sensor Port energy-in
- Actuator dcterms:hasPart Actuator Port energy-in
- Actuator dcterms:hasPart Actuator Port actuator-control-in
- Actuator dcterms:hasPart Actuator Port actuator-energy-out
- Information_Processing dcterms:hasPart Information_Processing Port human-machine-interface-server
- Information_Processing dcterms:hasPart Information_Processing Port actuator-control-out
- Information_Processing dcterms:hasPart Information_Processing Port sensor-reading-in
- Information_Processing dcterms:hasPart Information_Processing Port information-client
- Information_Processing dcterms:hasPart Information_Processing Port information-server
- Information_Processing dcterms:hasPart Information_Processing Port energy-in
- Human dcterms:hasPart Human Port human-machine-interface-client
- Electrical_Energy SpecIF:isAssociatedWith power
- Environment dcterms:hasPart Environment Port energy-out
- Environment dcterms:hasPart Environment Port material-out
- Environment dcterms:hasPart Environment Port energy-in
- Environment dcterms:hasPart Environment Port material-in
- Communication_System dcterms:hasPart Communication_System Port information-client
- Communication_System dcterms:hasPart Communication_System Port information-server
- Communication_System dcterms:hasPart Communication_System Port energy-in
- Mechatronic_System dcterms:hasPart basicSystem
- Mechatronic_System dcterms:hasPart Basic_System
- Mechatronic_System dcterms:hasPart sensor
- Mechatronic_System dcterms:hasPart actuator
- Mechatronic_System dcterms:hasPart informationProcessing
- Mechatronic_System dcterms:hasPart Information_Processing
- Mechatronic_System dcterms:hasPart Sensor
- Mechatronic_System dcterms:hasPart Actuator
- System dcterms:hasPart system
- Function SpecIF:isAssociatedWith requirement
- Requirement dcterms:hasPart requirement
- Function dcterms:hasPart function
- System SpecIF:isAssociatedWith function
- Mechatronic_System Port material-out SpecIF:provides Material
- Mechatronic_System Port material-in SpecIF:consumes Material
- Mechatronic_System Port energy-out SpecIF:provides Energy
- Mechatronic_System Port energy-in SpecIF:consumes Energy
- Mechatronic_System Port information-client SpecIF:handles Information
- Mechatronic_System Port information-server SpecIF:handles Information
- Mechatronic_System Port human-machine-interface-server SpecIF:handles Information
- Basic_System Port material-in SpecIF:consumes Material
- Basic_System Port material-out SpecIF:provides Material
- Basic_System Port energy-out SpecIF:provides Energy
- Basic_System Port energy-in SpecIF:consumes Energy
- Basic_System Port observed-value SpecIF:provides Sensor_Information
- Basic_System Port actuator-energy-in SpecIF:consumes Energy
- Sensor Port sensor-reading-out SpecIF:provides Sensor_Information
- Sensor Port sensed-value SpecIF:consumes Sensor_Information
- Sensor Port energy-in SpecIF:consumes Energy
- Actuator Port energy-in SpecIF:consumes Energy
- Actuator Port actuator-control-in SpecIF:consumes Actuator_Information
- Actuator Port actuator-energy-out SpecIF:provides Energy
- Information_Processing Port human-machine-interface-server SpecIF:handles Information
- Information_Processing Port actuator-control-out SpecIF:provides Actuator_Information
- Information_Processing Port sensor-reading-in SpecIF:consumes Sensor_Information
- Information_Processing Port information-client SpecIF:handles Information
- Information_Processing Port information-server SpecIF:handles Information
- Information_Processing Port energy-in SpecIF:consumes Energy
- Human Port human-machine-interface-client SpecIF:handles Information
- Environment Port energy-out SpecIF:provides Energy
- Environment Port material-out SpecIF:provides Material
- Environment Port energy-in SpecIF:consumes Energy
- Environment Port material-in SpecIF:consumes Material
- Communication_System Port information-client SpecIF:handles Information
- Communication_System Port information-server SpecIF:handles Information
- Communication_System Port energy-in SpecIF:consumes Energy
- Mechatronic_System Port material-in SpecIF:serves Basic_System Port material-in
- Basic_System Port material-out SpecIF:serves Mechatronic_System Port material-out
- Mechatronic_System Port energy-in SpecIF:serves Actuator Port energy-in
- Information_Processing Port human-machine-interface-server SpecIF:serves Mechatronic_System Port human-machine-interface-server
- Basic_System Port energy-out SpecIF:serves Mechatronic_System Port energy-out
- Mechatronic_System Port energy-in SpecIF:serves Basic_System Port energy-in
- Actuator Port actuator-control-in SpecIF:serves Information_Processing Port actuator-control-out
- Information_Processing Port information-client SpecIF:serves Mechatronic_System Port information-client
- Information_Processing Port information-server SpecIF:serves Mechatronic_System Port information-server
- Basic_System Port observed-value SpecIF:serves Sensor Port sensed-value
- Actuator Port actuator-energy-out SpecIF:serves Basic_System Port actuator-energy-in
- Sensor Port energy-in SpecIF:serves Mechatronic_System Port energy-in
- Information_Processing Port energy-in SpecIF:serves Mechatronic_System Port energy-in
- Mechatronic_System SpecIF:isSpecializationOf System
- basicSystem SpecIF:isSpecializationOf Basic_System
- sensor SpecIF:isSpecializationOf Sensor
- actuator SpecIF:isSpecializationOf Actuator
- informationProcessing SpecIF:isSpecializationOf Information_Processing
- Programmable_Mechatronic_System SpecIF:isSpecializationOf Mechatronic_System
- Cyber-Physical_System SpecIF:isSpecializationOf Mechatronic_System
- Water SpecIF:isSpecializationOf Material
- Simple_Mechatronic_System SpecIF:isSpecializationOf Mechatronic_System
- Sensor_Information SpecIF:isSpecializationOf Information
- Actuator_Information SpecIF:isSpecializationOf Information
- Electrical_Energy SpecIF:isSpecializationOf Energy
- system SpecIF:isSpecializationOf System
- function SpecIF:isSpecializationOf Function
- requirement SpecIF:isSpecializationOf Requirement
- Mechatronic_System_Environment SpecIF:shows Sensor_Information
- Mechatronic_System_Environment SpecIF:shows Communication_System Port energy-in
- Mechatronic_System_Environment SpecIF:shows Mechatronic_System Port material-in
- Mechatronic_System_Environment SpecIF:shows Material
- Mechatronic_System_Environment SpecIF:shows Mechatronic_System Port human-machine-interface-server
- Mechatronic_System_Environment SpecIF:shows sensor
- Mechatronic_System_Environment SpecIF:shows Actuator
- Mechatronic_System_Environment SpecIF:shows basicSystem
- Mechatronic_System_Environment SpecIF:shows Information_Processing
- Mechatronic_System_Environment SpecIF:shows Mechatronic_System
- Mechatronic_System_Environment SpecIF:shows Information
- Mechatronic_System_Environment SpecIF:shows Basic_System
- Mechatronic_System_Environment SpecIF:shows Mechatronic_System Port energy-out
- Mechatronic_System_Environment SpecIF:shows actuator
- Mechatronic_System_Environment SpecIF:shows Mechatronic_System Port material-out
- Mechatronic_System_Environment SpecIF:shows Communication_System
- Mechatronic_System_Environment SpecIF:shows Mechatronic_System Port information-client
- Mechatronic_System_Environment SpecIF:shows Human Port human-machine-interface-client
- Mechatronic_System_Environment SpecIF:shows Communication_System Port information-client
- Mechatronic_System_Environment SpecIF:shows Environment Port energy-in
- Mechatronic_System_Environment SpecIF:shows informationProcessing
- Mechatronic_System_Environment SpecIF:shows Actuator_Information
- Mechatronic_System_Environment SpecIF:shows Mechatronic_System Port information-server
- Mechatronic_System_Environment SpecIF:shows Energy
- Mechatronic_System_Environment SpecIF:shows Water
- Mechatronic_System_Environment SpecIF:shows Environment
- Mechatronic_System_Environment SpecIF:shows Environment Port energy-out
- Mechatronic_System_Environment SpecIF:shows Communication_System Port information-server
- Mechatronic_System_Environment SpecIF:shows Environment Port material-in
- Mechatronic_System_Environment SpecIF:shows Human
- Mechatronic_System_Environment SpecIF:shows Electrical_Energy
- Mechatronic_System_Environment SpecIF:shows Sensor
- Mechatronic_System_Environment SpecIF:shows Mechatronic_System Port energy-in
- Mechatronic_System_Environment SpecIF:shows Environment Port material-out
- Mechatronic_System_Design_Process SpecIF:shows Cyber-Physical_System
- Mechatronic_System_Design_Process SpecIF:shows informationProcessing
- Mechatronic_System_Design_Process SpecIF:shows sensor
- Mechatronic_System_Design_Process SpecIF:shows function
- Mechatronic_System_Design_Process SpecIF:shows System
- Mechatronic_System_Design_Process SpecIF:shows requirement
- Mechatronic_System_Design_Process SpecIF:shows Simple_Mechatronic_System
- Mechatronic_System_Design_Process SpecIF:shows basicSystem
- Mechatronic_System_Design_Process SpecIF:shows Mechatronic_System
- Mechatronic_System_Design_Process SpecIF:shows system
- Mechatronic_System_Design_Process SpecIF:shows actuator
- Mechatronic_System_Design_Process SpecIF:shows Programmable_Mechatronic_System
- Mechatronic_System_Design_Process SpecIF:shows Function
- Mechatronic_System_Design_Process SpecIF:shows Requirement
- Mechatronic_System SpecIF:shows Basic_System Port energy-out
- Mechatronic_System SpecIF:shows Information_Processing Port energy-in
- Mechatronic_System SpecIF:shows Mechatronic_System Port material-in
- Mechatronic_System SpecIF:shows Information_Processing Port sensor-reading-in
- Mechatronic_System SpecIF:shows Sensor Port sensor-reading-out
- Mechatronic_System SpecIF:shows Basic_System Port material-in
- Mechatronic_System SpecIF:shows Mechatronic_System Port human-machine-interface-server
- Mechatronic_System SpecIF:shows Basic_System Port actuator-energy-in
- Mechatronic_System SpecIF:shows Mechatronic_System Port energy-out
- Mechatronic_System SpecIF:shows Actuator Port actuator-control-in
- Mechatronic_System SpecIF:shows Mechatronic_System Port material-out
- Mechatronic_System SpecIF:shows Mechatronic_System Port information-client
- Mechatronic_System SpecIF:shows Basic_System Port energy-in
- Mechatronic_System SpecIF:shows Sensor Port energy-in
- Mechatronic_System SpecIF:shows Information_Processing Port information-client
- Mechatronic_System SpecIF:shows Sensor Port sensed-value
- Mechatronic_System SpecIF:shows Basic_System Port observed-value
- Mechatronic_System SpecIF:shows Actuator Port actuator-energy-out
- Mechatronic_System SpecIF:shows Actuator Port energy-in
- Mechatronic_System SpecIF:shows Information_Processing Port human-machine-interface-server
- Mechatronic_System SpecIF:shows Information_Processing Port information-server
- Mechatronic_System SpecIF:shows Mechatronic_System Port information-server
- Mechatronic_System SpecIF:shows Basic_System Port material-out
- Mechatronic_System SpecIF:shows Information_Processing Port actuator-control-out
- Mechatronic_System SpecIF:shows Mechatronic_System Port energy-in
- Mechatronic_System SpecIF:shows Mechatronic_System
- Mechatronic_System_Design_Process SpecIF:shows Basic_System
- Mechatronic_System SpecIF:shows Basic_System
- Mechatronic_System_Design_Process SpecIF:shows Information_Processing
- Mechatronic_System SpecIF:shows Information_Processing
- Mechatronic_System_Design_Process SpecIF:shows Sensor
- Mechatronic_System SpecIF:shows Sensor
- Mechatronic_System_Design_Process SpecIF:shows Actuator
- Mechatronic_System SpecIF:shows Actuator

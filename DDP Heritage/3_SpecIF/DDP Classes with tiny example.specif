# SpecIF Classes for prostep iViP DDP (Data Model)
SpecIF Classes derived from DDP Schema Version 2.0 created 10.03.2023 08:09:28 by Michael Kirsch, :em engineering methods AG on behalf of prostep iViP Association
- Rights: Creative Commons 4.0 CC BY-SA, https://creativecommons.org/licenses/by-sa/4.0/

## Dr. (Person)
- firstname: Alice
- lastname: Clever
- mail: alice.clever@mymail.org
- phone: +1 503 6677223

## acme (OrganizationUnit)
- number: 123
- dc:description: acme Corp.

## Statements
- Dr. (Person) MemberOf (OrganizationUnit) acme

# prostep iViP DDP (Ontology)
Ontology derived from DDP Schema Version 2.0 created 10.03.2023 08:09:28 by Michael Kirsch, :em engineering methods AG on behalf of prostep iViP Association
- Rights: Creative Commons 4.0 CC BY-SA, https://creativecommons.org/licenses/by-sa/4.0/

## SpecIF Ontology (SpecIF:Heading)
- dcterms:type: W3C:Ontology

## Resource Class Terms (SpecIF:Heading)
- dcterms:description: A resource represents an artefact, e.g. a model element or a requirement. The terms listed in this chapter may be used to distinguish different classes (types) of artefacts constituting a system specification. A resource may serve as subject or as object in a subject-predicate-object statement. Each resource class may define an individual set of properties for carrying the information 'payload'.
  A resource class corresponds to a 'SPEC-OBJECT-TYPE' and a resource is a 'SPEC-OBJECT' in the Requirements Interchange Format (ReqIF). In ArchiMate® 3.0, a resource is an Element.

## DDP:Role (SpecIF:TermResourceClass)
- dcterms:description: A defined function to be performed by a project team member, such as testing, filing, inspecting, coding.
  https://intranet.prostep.org/display/PROJ/Glossary
- SpecIF:LocalTerm: Role
- SpecIF:TermStatus: SpecIF:LifecycleStatusReleased
- SpecIF:Domain: SpecIF:DomainSystemsEngineering
- SpecIF:Instantiation: SpecIF:InstantiationAuto, SpecIF:InstantiationUser

## DDP:Person (SpecIF:TermResourceClass)
- dcterms:description: Represents a real person, but may also be a system user that appears in source data. The FOAF (Friend of a Friend) Ontology has been considered, but is not used as it does not provide a structured representation for firstname, lastname and title of a person.
- SpecIF:LocalTerm: Person
- SpecIF:TermStatus: SpecIF:LifecycleStatusReleased
- SpecIF:Domain: SpecIF:DomainSystemsEngineering
- SpecIF:Instantiation: SpecIF:InstantiationAuto, SpecIF:InstantiationUser

## DDP:OrganizationUnit (SpecIF:TermResourceClass)
- dcterms:description: An organization unit is part of a corporate structure. It comprises persons as well as sub-organization units.
- SpecIF:LocalTerm: OrganizationUnit
- SpecIF:TermStatus: SpecIF:LifecycleStatusReleased
- SpecIF:Domain: SpecIF:DomainSystemsEngineering
- SpecIF:Instantiation: SpecIF:InstantiationAuto, SpecIF:InstantiationUser

## DDP:Task (SpecIF:TermResourceClass)
- dcterms:description: A task is a definite piece of work assigned to a person or organisation
- SpecIF:LocalTerm: Task
- SpecIF:TermStatus: SpecIF:LifecycleStatusReleased
- SpecIF:Domain: SpecIF:DomainSystemsEngineering
- SpecIF:Instantiation: SpecIF:InstantiationAuto, SpecIF:InstantiationUser

## DDP:Project (SpecIF:TermResourceClass)
- dcterms:description: Represents a project or sub-project
- SpecIF:LocalTerm: Project
- SpecIF:TermStatus: SpecIF:LifecycleStatusReleased
- SpecIF:Domain: SpecIF:DomainSystemsEngineering
- SpecIF:Instantiation: SpecIF:InstantiationAuto, SpecIF:InstantiationUser

## DDP:UseCase (SpecIF:TermResourceClass)
- dcterms:description: Specifies what the user of a product will do in order to achieve a goal
- SpecIF:LocalTerm: UseCase
- SpecIF:TermStatus: SpecIF:LifecycleStatusReleased
- SpecIF:Domain: SpecIF:DomainSystemsEngineering
- SpecIF:Instantiation: SpecIF:InstantiationAuto, SpecIF:InstantiationUser

## DDP:Requirement (SpecIF:TermResourceClass)
- dcterms:description: Characteristics that identify the accomplishment levels needed to achieve specific objectives for a given set of conditions.
  Requirements can be 'must have', 'can have' and 'nice to have'.
  A. A condition or capability needed by a user to solve a problem or achieve an objective.
  B. A condition or capability that must be met or possessed by a system or system component to satisfy a contract, standard, specification, or other formally imposed document.
  C. A documented representation of a condition or capability as in definition (A:) or (B).
  https://intranet.prostep.org/display/PROJ/Glossary
- SpecIF:LocalTerm: Requirement
- SpecIF:TermStatus: SpecIF:LifecycleStatusReleased
- SpecIF:Domain: SpecIF:DomainSystemsEngineering
- SpecIF:Instantiation: SpecIF:InstantiationAuto, SpecIF:InstantiationUser

## DDP:ProductFunction (SpecIF:TermResourceClass)
- dcterms:description: A product function describes the way a system works or performs a specific task.
- SpecIF:LocalTerm: ProductFunction
- SpecIF:TermStatus: SpecIF:LifecycleStatusReleased
- SpecIF:Domain: SpecIF:DomainSystemsEngineering
- SpecIF:Instantiation: SpecIF:InstantiationAuto, SpecIF:InstantiationUser

## DDP:SystemComponent (SpecIF:TermResourceClass)
- dcterms:description: Represents a generic component of a system
- SpecIF:LocalTerm: SystemComponent
- SpecIF:TermStatus: SpecIF:LifecycleStatusReleased
- SpecIF:Domain: SpecIF:DomainSystemsEngineering
- SpecIF:Instantiation: SpecIF:InstantiationAuto, SpecIF:InstantiationUser

## DDP:ComponentInterface (SpecIF:TermResourceClass)
- dcterms:description: Represents a generic interface of a system component
- SpecIF:LocalTerm: ComponentInterface
- SpecIF:TermStatus: SpecIF:LifecycleStatusReleased
- SpecIF:Domain: SpecIF:DomainSystemsEngineering
- SpecIF:Instantiation: SpecIF:InstantiationAuto, SpecIF:InstantiationUser

## DDP:ComponentConnection (SpecIF:TermResourceClass)
- dcterms:description: Represents a connection between two components through interfaces
- SpecIF:LocalTerm: ComponentConnection
- SpecIF:TermStatus: SpecIF:LifecycleStatusReleased
- SpecIF:Domain: SpecIF:DomainSystemsEngineering
- SpecIF:Instantiation: SpecIF:InstantiationAuto, SpecIF:InstantiationUser

## DDP:ComponentState (SpecIF:TermResourceClass)
- dcterms:description: Represents the condition of a system component. Can be it a value, a condition, an information storage or a physical shape.
- SpecIF:LocalTerm: ComponentState
- SpecIF:TermStatus: SpecIF:LifecycleStatusReleased
- SpecIF:Domain: SpecIF:DomainSystemsEngineering
- SpecIF:Instantiation: SpecIF:InstantiationAuto, SpecIF:InstantiationUser

## DDP:MechanicalComponent (SpecIF:TermResourceClass)
- dcterms:description: Represents a single mechanical part, an assembly or the entire product
- SpecIF:LocalTerm: MechanicalComponent
- SpecIF:TermStatus: SpecIF:LifecycleStatusReleased
- SpecIF:Domain: SpecIF:DomainSystemsEngineering
- SpecIF:Instantiation: SpecIF:InstantiationAuto, SpecIF:InstantiationUser

## DDP:MechanicalComponentInstance (SpecIF:TermResourceClass)
- dcterms:description: Represents a specific instance of a mechanical component in a product structure
- SpecIF:LocalTerm: MechanicalComponentInstance
- SpecIF:TermStatus: SpecIF:LifecycleStatusReleased
- SpecIF:Domain: SpecIF:DomainSystemsEngineering
- SpecIF:Instantiation: SpecIF:InstantiationAuto, SpecIF:InstantiationUser

## DDP:Material (SpecIF:TermResourceClass)
- dcterms:description: Material assigned to the mechanical component
- SpecIF:LocalTerm: Material
- SpecIF:TermStatus: SpecIF:LifecycleStatusReleased
- SpecIF:Domain: SpecIF:DomainSystemsEngineering
- SpecIF:Instantiation: SpecIF:InstantiationAuto, SpecIF:InstantiationUser

## DDP:ModelView (SpecIF:TermResourceClass)
- dcterms:description: Represents a view of product geometry, including the definition of the viewpoint, and the visibility of components and annotations
- SpecIF:LocalTerm: ModelView
- SpecIF:TermStatus: SpecIF:LifecycleStatusReleased
- SpecIF:Domain: SpecIF:DomainSystemsEngineering
- SpecIF:Instantiation: SpecIF:InstantiationAuto, SpecIF:InstantiationUser

## DDP:ModelAnnotation (SpecIF:TermResourceClass)
- dcterms:description: A text annotation, dimension, tolerance, surface specification, etc. with relation to product geometry
- SpecIF:LocalTerm: ModelAnnotation
- SpecIF:TermStatus: SpecIF:LifecycleStatusReleased
- SpecIF:Domain: SpecIF:DomainSystemsEngineering
- SpecIF:Instantiation: SpecIF:InstantiationAuto, SpecIF:InstantiationUser

## DDP:KinematicMechanism (SpecIF:TermResourceClass)
- dcterms:description: Represents a kinematic mechanism
- SpecIF:LocalTerm: KinematicMechanism
- SpecIF:TermStatus: SpecIF:LifecycleStatusReleased
- SpecIF:Domain: SpecIF:DomainSystemsEngineering
- SpecIF:Instantiation: SpecIF:InstantiationAuto, SpecIF:InstantiationUser

## DDP:KinematicJoint (SpecIF:TermResourceClass)
- dcterms:description: Represents a kinematic joint between a pair of component instances
- SpecIF:LocalTerm: KinematicJoint
- SpecIF:TermStatus: SpecIF:LifecycleStatusReleased
- SpecIF:Domain: SpecIF:DomainSystemsEngineering
- SpecIF:Instantiation: SpecIF:InstantiationAuto, SpecIF:InstantiationUser

## DDP:KinematicSensor (SpecIF:TermResourceClass)
- dcterms:description: Represents a kinematic sensor
- SpecIF:LocalTerm: KinematicSensor
- SpecIF:TermStatus: SpecIF:LifecycleStatusReleased
- SpecIF:Domain: SpecIF:DomainSystemsEngineering
- SpecIF:Instantiation: SpecIF:InstantiationAuto, SpecIF:InstantiationUser

## DDP:KinematicMotion (SpecIF:TermResourceClass)
- dcterms:description: Represents a kinematic motion
- SpecIF:LocalTerm: KinematicMotion
- SpecIF:TermStatus: SpecIF:LifecycleStatusReleased
- SpecIF:Domain: SpecIF:DomainSystemsEngineering
- SpecIF:Instantiation: SpecIF:InstantiationAuto, SpecIF:InstantiationUser

## DDP:JoiningProcess (SpecIF:TermResourceClass)
- dcterms:description: Represents a joining process type such as welding, riveting, etc.
- SpecIF:LocalTerm: JoiningProcess
- SpecIF:TermStatus: SpecIF:LifecycleStatusReleased
- SpecIF:Domain: SpecIF:DomainSystemsEngineering
- SpecIF:Instantiation: SpecIF:InstantiationAuto, SpecIF:InstantiationUser

## DDP:JoiningElement (SpecIF:TermResourceClass)
- dcterms:description: Represents a joining element such as a welding spot, a rivet, etc.
- SpecIF:LocalTerm: JoiningElement
- SpecIF:TermStatus: SpecIF:LifecycleStatusReleased
- SpecIF:Domain: SpecIF:DomainSystemsEngineering
- SpecIF:Instantiation: SpecIF:InstantiationAuto, SpecIF:InstantiationUser

## DDP:ElectricElectronicComponent (SpecIF:TermResourceClass)
- dcterms:description: Represents an electric/electronic component
- SpecIF:LocalTerm: ElectricElectronicComponent
- SpecIF:TermStatus: SpecIF:LifecycleStatusReleased
- SpecIF:Domain: SpecIF:DomainSystemsEngineering
- SpecIF:Instantiation: SpecIF:InstantiationAuto, SpecIF:InstantiationUser

## DDP:ElectricElectronicPort (SpecIF:TermResourceClass)
- dcterms:description: Represents an electric/electronic port on an electric/electronic component
- SpecIF:LocalTerm: ElectricElectronicPort
- SpecIF:TermStatus: SpecIF:LifecycleStatusReleased
- SpecIF:Domain: SpecIF:DomainSystemsEngineering
- SpecIF:Instantiation: SpecIF:InstantiationAuto, SpecIF:InstantiationUser

## DDP:ElectricElectronicConnection (SpecIF:TermResourceClass)
- dcterms:description: Represents an electric/electronic connection
- SpecIF:LocalTerm: ElectricElectronicConnection
- SpecIF:TermStatus: SpecIF:LifecycleStatusReleased
- SpecIF:Domain: SpecIF:DomainSystemsEngineering
- SpecIF:Instantiation: SpecIF:InstantiationAuto, SpecIF:InstantiationUser

## DDP:SoftwareClass (SpecIF:TermResourceClass)
- dcterms:description: A class in source code that represents a logical collection data and functions
- SpecIF:LocalTerm: SoftwareClass
- SpecIF:TermStatus: SpecIF:LifecycleStatusReleased
- SpecIF:Domain: SpecIF:DomainSystemsEngineering
- SpecIF:Instantiation: SpecIF:InstantiationAuto, SpecIF:InstantiationUser

## DDP:SoftwareInterface (SpecIF:TermResourceClass)
- dcterms:description: An interface in source code that allows a class to interact with other components of a software
- SpecIF:LocalTerm: SoftwareInterface
- SpecIF:TermStatus: SpecIF:LifecycleStatusReleased
- SpecIF:Domain: SpecIF:DomainSystemsEngineering
- SpecIF:Instantiation: SpecIF:InstantiationAuto, SpecIF:InstantiationUser

## DDP:SoftwareComponent (SpecIF:TermResourceClass)
- dcterms:description: A compiled component of software to be used in a product, i. e. executable or library
- SpecIF:LocalTerm: SoftwareComponent
- SpecIF:TermStatus: SpecIF:LifecycleStatusReleased
- SpecIF:Domain: SpecIF:DomainSystemsEngineering
- SpecIF:Instantiation: SpecIF:InstantiationAuto, SpecIF:InstantiationUser

## DDP:HydraulicPneumaticConnection (SpecIF:TermResourceClass)
- dcterms:description: Represents a hydraulic or pneumatic connection, i. e. a tube or hose
- SpecIF:LocalTerm: HydraulicPneumaticConnection
- SpecIF:TermStatus: SpecIF:LifecycleStatusReleased
- SpecIF:Domain: SpecIF:DomainSystemsEngineering
- SpecIF:Instantiation: SpecIF:InstantiationAuto, SpecIF:InstantiationUser

## DDP:HydraulicPneumaticPort (SpecIF:TermResourceClass)
- dcterms:description: Represents a hydraulic or pneumatic port on a mechanical component
- SpecIF:LocalTerm: HydraulicPneumaticPort
- SpecIF:TermStatus: SpecIF:LifecycleStatusReleased
- SpecIF:Domain: SpecIF:DomainSystemsEngineering
- SpecIF:Instantiation: SpecIF:InstantiationAuto, SpecIF:InstantiationUser

## DDP:ValidationPlan (SpecIF:TermResourceClass)
- dcterms:description: A specific executable test that examines all aspects including inputs and outputs of a system and then provides a detailed description of the steps that should be taken, the results that should be achieved, and other elements that should be identified. Steps explained in a test case include all details even if they are assumed to be common knowledge. Test cases are used as a technical explanation and reference guide for systems.
  https://intranet.prostep.org/display/PROJ/Glossary
- SpecIF:LocalTerm: ValidationPlan
- SpecIF:TermStatus: SpecIF:LifecycleStatusReleased
- SpecIF:Domain: SpecIF:DomainSystemsEngineering
- SpecIF:Instantiation: SpecIF:InstantiationAuto, SpecIF:InstantiationUser

## DDP:ValidationBoundaryCondition (SpecIF:TermResourceClass)
- dcterms:description: Validation boundary condition, i. e. force, pressure, temperature or time.
- SpecIF:LocalTerm: ValidationBoundaryCondition
- SpecIF:TermStatus: SpecIF:LifecycleStatusReleased
- SpecIF:Domain: SpecIF:DomainSystemsEngineering
- SpecIF:Instantiation: SpecIF:InstantiationAuto, SpecIF:InstantiationUser

## DDP:ValidationRun (SpecIF:TermResourceClass)
- dcterms:description: Vorgang einer Validierung
- SpecIF:LocalTerm: ValidationRun
- SpecIF:TermStatus: SpecIF:LifecycleStatusReleased
- SpecIF:Domain: SpecIF:DomainSystemsEngineering
- SpecIF:Instantiation: SpecIF:InstantiationAuto, SpecIF:InstantiationUser

## DDP:ValidationResult (SpecIF:TermResourceClass)
- dcterms:description: Ergebnis einer Validierung
- SpecIF:LocalTerm: ValidationResult
- SpecIF:TermStatus: SpecIF:LifecycleStatusReleased
- SpecIF:Domain: SpecIF:DomainSystemsEngineering
- SpecIF:Instantiation: SpecIF:InstantiationAuto, SpecIF:InstantiationUser

## DDP:ManufacturingOperation (SpecIF:TermResourceClass)
- dcterms:description: Represents a single or a group of manufacturing operation that lead to a finished, assembled product.
- SpecIF:LocalTerm: ManufacturingOperation
- SpecIF:TermStatus: SpecIF:LifecycleStatusReleased
- SpecIF:Domain: SpecIF:DomainSystemsEngineering
- SpecIF:Instantiation: SpecIF:InstantiationAuto, SpecIF:InstantiationUser

## DDP:ManufacturingEquipmentComponent (SpecIF:TermResourceClass)
- dcterms:description: Represents all kinds of tools and equipment used to manufacture parts and assemble the product.
- SpecIF:LocalTerm: ManufacturingEquipmentComponent
- SpecIF:TermStatus: SpecIF:LifecycleStatusReleased
- SpecIF:Domain: SpecIF:DomainSystemsEngineering
- SpecIF:Instantiation: SpecIF:InstantiationAuto, SpecIF:InstantiationUser

## DDP:InspectionCharacteristic (SpecIF:TermResourceClass)
- dcterms:description: Represents a characteristic that must be inspected to ensure product function.
- SpecIF:LocalTerm: InspectionCharacteristic
- SpecIF:TermStatus: SpecIF:LifecycleStatusReleased
- SpecIF:Domain: SpecIF:DomainSystemsEngineering
- SpecIF:Instantiation: SpecIF:InstantiationAuto, SpecIF:InstantiationUser

## DDP:InspectionPlan (SpecIF:TermResourceClass)
- dcterms:description: Specifies what characteristics must be inspected using which equipment for which purpose.
- SpecIF:LocalTerm: InspectionPlan
- SpecIF:TermStatus: SpecIF:LifecycleStatusReleased
- SpecIF:Domain: SpecIF:DomainSystemsEngineering
- SpecIF:Instantiation: SpecIF:InstantiationAuto, SpecIF:InstantiationUser

## DDP:InspectionResource (SpecIF:TermResourceClass)
- dcterms:description: Represents a mechanical component used as an inspection resource
- SpecIF:LocalTerm: InspectionResource
- SpecIF:TermStatus: SpecIF:LifecycleStatusReleased
- SpecIF:Domain: SpecIF:DomainSystemsEngineering
- SpecIF:Instantiation: SpecIF:InstantiationAuto, SpecIF:InstantiationUser

## DDP:InspectionRun (SpecIF:TermResourceClass)
- dcterms:description: Represents an inspection run that collects inspection results for each inspection characteristic allocated to an inspection plan.
- SpecIF:LocalTerm: InspectionRun
- SpecIF:TermStatus: SpecIF:LifecycleStatusReleased
- SpecIF:Domain: SpecIF:DomainSystemsEngineering
- SpecIF:Instantiation: SpecIF:InstantiationAuto, SpecIF:InstantiationUser

## DDP:InspectionResult (SpecIF:TermResourceClass)
- dcterms:description: Represents an inspection result for an inspection criterium
- SpecIF:LocalTerm: InspectionResult
- SpecIF:TermStatus: SpecIF:LifecycleStatusReleased
- SpecIF:Domain: SpecIF:DomainSystemsEngineering
- SpecIF:Instantiation: SpecIF:InstantiationAuto, SpecIF:InstantiationUser

## DDP:Revision (SpecIF:TermResourceClass)
- dcterms:description: Represents a revision as a context for other elements to be valid. The datamodel allows selected elements to be related to a revision, i. e. mechanical components.
- SpecIF:LocalTerm: Revision
- SpecIF:TermStatus: SpecIF:LifecycleStatusReleased
- SpecIF:Domain: SpecIF:DomainSystemsEngineering
- SpecIF:Instantiation: SpecIF:InstantiationAuto, SpecIF:InstantiationUser

## DDP:Configuration (SpecIF:TermResourceClass)
- dcterms:description: Represents a configuration as a context for other elements to be valid. The datamodel allows selected elements to be related to a revision, i. e. mechanical components
- SpecIF:LocalTerm: Configuration
- SpecIF:TermStatus: SpecIF:LifecycleStatusReleased
- SpecIF:Domain: SpecIF:DomainSystemsEngineering
- SpecIF:Instantiation: SpecIF:InstantiationAuto, SpecIF:InstantiationUser

## Statement Class Terms (SpecIF:Heading)
- dcterms:description: A statement represents a logic affinity or association between two resources, i.e. system specification artefacts. The terms listed in this chapter may be used as predicates to distinguish different classes (types) of statements. Each statement class may define an individual set of properties for carrying the information 'payload'.
  In SpecIF, a statement is first order predicate logic. For each predicate (statement class), a list of eligible resource classes may be defined for subjects and objects, respectively. For example, the predicate [[oslc_rm:satisfies]] is usually confined to [[FMC:Actor]] and [[FMC:State]] as subject and [[IREB:Requirement]] as object.
  A statement consisting of subject-predicate-object (where a resource may serve as subject or object) can be directly mapped to a ReqIF relation, a RDF triple in OSLC or 'linked data' in general.
  A statement class corresponds to a 'SPEC-RELATION-TYPE' and a statement is a 'SPEC-RELATION' in the Requirements Interchange Format (ReqIF). In ArchiMate® 3.0, a statement is a Relationship.

## DDP:RolePartOfRole (SpecIF:TermStatementClass)
- dcterms:description: Superior element
- SpecIF:LocalTerm: (Role) PartOf (Role)
- SpecIF:TermStatus: SpecIF:LifecycleStatusReleased
- SpecIF:Domain: SpecIF:DomainSystemsEngineering
- SpecIF:Instantiation: SpecIF:InstantiationAuto, SpecIF:InstantiationUser

## DDP:RoleSpecialismOfRole (SpecIF:TermStatementClass)
- dcterms:description: More generic item
- SpecIF:LocalTerm: (Role) SpecialismOf (Role)
- SpecIF:TermStatus: SpecIF:LifecycleStatusReleased
- SpecIF:Domain: SpecIF:DomainSystemsEngineering
- SpecIF:Instantiation: SpecIF:InstantiationAuto, SpecIF:InstantiationUser

## DDP:PersonMemberOfOrganizationUnit (SpecIF:TermStatementClass)
- dcterms:description: Organization unit the person is a member of
- SpecIF:LocalTerm: (Person) MemberOf (OrganizationUnit)
- SpecIF:TermStatus: SpecIF:LifecycleStatusReleased
- SpecIF:Domain: SpecIF:DomainSystemsEngineering
- SpecIF:Instantiation: SpecIF:InstantiationAuto, SpecIF:InstantiationUser

## DDP:OrganizationUnitPartOfOrganizationUnit (SpecIF:TermStatementClass)
- dcterms:description: Superior element
- SpecIF:LocalTerm: (OrganizationUnit) PartOf (OrganizationUnit)
- SpecIF:TermStatus: SpecIF:LifecycleStatusReleased
- SpecIF:Domain: SpecIF:DomainSystemsEngineering
- SpecIF:Instantiation: SpecIF:InstantiationAuto, SpecIF:InstantiationUser

## DDP:TaskPartOfTask (SpecIF:TermStatementClass)
- dcterms:description: Superior element
- SpecIF:LocalTerm: (Task) PartOf (Task)
- SpecIF:TermStatus: SpecIF:LifecycleStatusReleased
- SpecIF:Domain: SpecIF:DomainSystemsEngineering
- SpecIF:Instantiation: SpecIF:InstantiationAuto, SpecIF:InstantiationUser

## DDP:TaskCreatedByPerson (SpecIF:TermStatementClass)
- dcterms:description: The person who created this task
- SpecIF:LocalTerm: (Task) CreatedBy (Person)
- SpecIF:TermStatus: SpecIF:LifecycleStatusReleased
- SpecIF:Domain: SpecIF:DomainSystemsEngineering
- SpecIF:Instantiation: SpecIF:InstantiationAuto, SpecIF:InstantiationUser

## DDP:TaskAssignedToPerson (SpecIF:TermStatementClass)
- dcterms:description: The person this task is assigned to
- SpecIF:LocalTerm: (Task) AssignedTo (Person)
- SpecIF:TermStatus: SpecIF:LifecycleStatusReleased
- SpecIF:Domain: SpecIF:DomainSystemsEngineering
- SpecIF:Instantiation: SpecIF:InstantiationAuto, SpecIF:InstantiationUser

## DDP:TaskConductedByOrganizationUnit (SpecIF:TermStatementClass)
- dcterms:description: Organization unit this task is conduted by
- SpecIF:LocalTerm: (Task) ConductedBy (OrganizationUnit)
- SpecIF:TermStatus: SpecIF:LifecycleStatusReleased
- SpecIF:Domain: SpecIF:DomainSystemsEngineering
- SpecIF:Instantiation: SpecIF:InstantiationAuto, SpecIF:InstantiationUser

## DDP:ProjectPartOfProject (SpecIF:TermStatementClass)
- dcterms:description: Superior element
- SpecIF:LocalTerm: (Project) PartOf (Project)
- SpecIF:TermStatus: SpecIF:LifecycleStatusReleased
- SpecIF:Domain: SpecIF:DomainSystemsEngineering
- SpecIF:Instantiation: SpecIF:InstantiationAuto, SpecIF:InstantiationUser

## DDP:ProjectCreatedByPerson (SpecIF:TermStatementClass)
- dcterms:description: The person who created this task
- SpecIF:LocalTerm: (Project) CreatedBy (Person)
- SpecIF:TermStatus: SpecIF:LifecycleStatusReleased
- SpecIF:Domain: SpecIF:DomainSystemsEngineering
- SpecIF:Instantiation: SpecIF:InstantiationAuto, SpecIF:InstantiationUser

## DDP:ProjectAssignedToPerson (SpecIF:TermStatementClass)
- dcterms:description: The person this task is assigned to
- SpecIF:LocalTerm: (Project) AssignedTo (Person)
- SpecIF:TermStatus: SpecIF:LifecycleStatusReleased
- SpecIF:Domain: SpecIF:DomainSystemsEngineering
- SpecIF:Instantiation: SpecIF:InstantiationAuto, SpecIF:InstantiationUser

## DDP:ProjectConductedByOrganizationUnit (SpecIF:TermStatementClass)
- dcterms:description: Organization unit this task is conduted by
- SpecIF:LocalTerm: (Project) ConductedBy (OrganizationUnit)
- SpecIF:TermStatus: SpecIF:LifecycleStatusReleased
- SpecIF:Domain: SpecIF:DomainSystemsEngineering
- SpecIF:Instantiation: SpecIF:InstantiationAuto, SpecIF:InstantiationUser

## DDP:UseCasePartOfUseCase (SpecIF:TermStatementClass)
- dcterms:description: Superior element
- SpecIF:LocalTerm: (UseCase) PartOf (UseCase)
- SpecIF:TermStatus: SpecIF:LifecycleStatusReleased
- SpecIF:Domain: SpecIF:DomainSystemsEngineering
- SpecIF:Instantiation: SpecIF:InstantiationAuto, SpecIF:InstantiationUser

## DDP:UseCaseSpecialismOfUseCase (SpecIF:TermStatementClass)
- dcterms:description: More generic item
- SpecIF:LocalTerm: (UseCase) SpecialismOf (UseCase)
- SpecIF:TermStatus: SpecIF:LifecycleStatusReleased
- SpecIF:Domain: SpecIF:DomainSystemsEngineering
- SpecIF:Instantiation: SpecIF:InstantiationAuto, SpecIF:InstantiationUser

## DDP:UseCaseRelatesToConfiguration (SpecIF:TermStatementClass)
- dcterms:description: Relation to a configuration
- SpecIF:LocalTerm: (UseCase) RelatesTo (Configuration)
- SpecIF:TermStatus: SpecIF:LifecycleStatusReleased
- SpecIF:Domain: SpecIF:DomainSystemsEngineering
- SpecIF:Instantiation: SpecIF:InstantiationAuto, SpecIF:InstantiationUser

## DDP:UseCaseOwnedByPerson (SpecIF:TermStatementClass)
- dcterms:description: The role owning this use case
- SpecIF:LocalTerm: (UseCase) OwnedBy (Person)
- SpecIF:TermStatus: SpecIF:LifecycleStatusReleased
- SpecIF:Domain: SpecIF:DomainSystemsEngineering
- SpecIF:Instantiation: SpecIF:InstantiationAuto, SpecIF:InstantiationUser

## DDP:UseCaseAbstractionOfUseCase (SpecIF:TermStatementClass)
- dcterms:description: A more specific use case this use case is an abstraction of.
- SpecIF:LocalTerm: (UseCase) AbstractionOf (UseCase)
- SpecIF:TermStatus: SpecIF:LifecycleStatusReleased
- SpecIF:Domain: SpecIF:DomainSystemsEngineering
- SpecIF:Instantiation: SpecIF:InstantiationAuto, SpecIF:InstantiationUser

## DDP:UseCaseCreatedByPerson (SpecIF:TermStatementClass)
- dcterms:description: The person who created this use case
- SpecIF:LocalTerm: (UseCase) CreatedBy (Person)
- SpecIF:TermStatus: SpecIF:LifecycleStatusReleased
- SpecIF:Domain: SpecIF:DomainSystemsEngineering
- SpecIF:Instantiation: SpecIF:InstantiationAuto, SpecIF:InstantiationUser

## DDP:RequirementPartOfRequirement (SpecIF:TermStatementClass)
- dcterms:description: Superior element
- SpecIF:LocalTerm: (Requirement) PartOf (Requirement)
- SpecIF:TermStatus: SpecIF:LifecycleStatusReleased
- SpecIF:Domain: SpecIF:DomainSystemsEngineering
- SpecIF:Instantiation: SpecIF:InstantiationAuto, SpecIF:InstantiationUser

## DDP:RequirementSpecialismOfRequirement (SpecIF:TermStatementClass)
- dcterms:description: More generic item
- SpecIF:LocalTerm: (Requirement) SpecialismOf (Requirement)
- SpecIF:TermStatus: SpecIF:LifecycleStatusReleased
- SpecIF:Domain: SpecIF:DomainSystemsEngineering
- SpecIF:Instantiation: SpecIF:InstantiationAuto, SpecIF:InstantiationUser

## DDP:RequirementRelatesToRevision (SpecIF:TermStatementClass)
- dcterms:description: Relation to a version
- SpecIF:LocalTerm: (Requirement) RelatesTo (Revision)
- SpecIF:TermStatus: SpecIF:LifecycleStatusReleased
- SpecIF:Domain: SpecIF:DomainSystemsEngineering
- SpecIF:Instantiation: SpecIF:InstantiationAuto, SpecIF:InstantiationUser

## DDP:RequirementRelatesToConfiguration (SpecIF:TermStatementClass)
- dcterms:description: Relation to a configuration
- SpecIF:LocalTerm: (Requirement) RelatesTo (Configuration)
- SpecIF:TermStatus: SpecIF:LifecycleStatusReleased
- SpecIF:Domain: SpecIF:DomainSystemsEngineering
- SpecIF:Instantiation: SpecIF:InstantiationAuto, SpecIF:InstantiationUser

## DDP:RequirementCreatedByPerson (SpecIF:TermStatementClass)
- dcterms:description: The person who created this requirement
- SpecIF:LocalTerm: (Requirement) CreatedBy (Person)
- SpecIF:TermStatus: SpecIF:LifecycleStatusReleased
- SpecIF:Domain: SpecIF:DomainSystemsEngineering
- SpecIF:Instantiation: SpecIF:InstantiationAuto, SpecIF:InstantiationUser

## DDP:RequirementRelatedToSystemComponent (SpecIF:TermStatementClass)
- dcterms:description: System component this requirement relates to.
- SpecIF:LocalTerm: (Requirement) RelatedTo (SystemComponent)
- SpecIF:TermStatus: SpecIF:LifecycleStatusReleased
- SpecIF:Domain: SpecIF:DomainSystemsEngineering
- SpecIF:Instantiation: SpecIF:InstantiationAuto, SpecIF:InstantiationUser

## DDP:ProductFunctionPartOfProductFunction (SpecIF:TermStatementClass)
- dcterms:description: Superior element
- SpecIF:LocalTerm: (ProductFunction) PartOf (ProductFunction)
- SpecIF:TermStatus: SpecIF:LifecycleStatusReleased
- SpecIF:Domain: SpecIF:DomainSystemsEngineering
- SpecIF:Instantiation: SpecIF:InstantiationAuto, SpecIF:InstantiationUser

## DDP:ProductFunctionSpecialismOfProductFunction (SpecIF:TermStatementClass)
- dcterms:description: More generic item
- SpecIF:LocalTerm: (ProductFunction) SpecialismOf (ProductFunction)
- SpecIF:TermStatus: SpecIF:LifecycleStatusReleased
- SpecIF:Domain: SpecIF:DomainSystemsEngineering
- SpecIF:Instantiation: SpecIF:InstantiationAuto, SpecIF:InstantiationUser

## DDP:ProductFunctionRelatesToRevision (SpecIF:TermStatementClass)
- dcterms:description: Relation to a version
- SpecIF:LocalTerm: (ProductFunction) RelatesTo (Revision)
- SpecIF:TermStatus: SpecIF:LifecycleStatusReleased
- SpecIF:Domain: SpecIF:DomainSystemsEngineering
- SpecIF:Instantiation: SpecIF:InstantiationAuto, SpecIF:InstantiationUser

## DDP:ProductFunctionRelatesToConfiguration (SpecIF:TermStatementClass)
- dcterms:description: Relation to a configuration
- SpecIF:LocalTerm: (ProductFunction) RelatesTo (Configuration)
- SpecIF:TermStatus: SpecIF:LifecycleStatusReleased
- SpecIF:Domain: SpecIF:DomainSystemsEngineering
- SpecIF:Instantiation: SpecIF:InstantiationAuto, SpecIF:InstantiationUser

## DDP:ProductFunctionFollowsProductFunction (SpecIF:TermStatementClass)
- dcterms:description: In a sequence of product functions, specifies the previous product function.
- SpecIF:LocalTerm: (ProductFunction) Follows (ProductFunction)
- SpecIF:TermStatus: SpecIF:LifecycleStatusReleased
- SpecIF:Domain: SpecIF:DomainSystemsEngineering
- SpecIF:Instantiation: SpecIF:InstantiationAuto, SpecIF:InstantiationUser

## DDP:ProductFunctionFulfilsRequirement (SpecIF:TermStatementClass)
- dcterms:description: Requirement fulfilled by this product function
- SpecIF:LocalTerm: (ProductFunction) Fulfils (Requirement)
- SpecIF:TermStatus: SpecIF:LifecycleStatusReleased
- SpecIF:Domain: SpecIF:DomainSystemsEngineering
- SpecIF:Instantiation: SpecIF:InstantiationAuto, SpecIF:InstantiationUser

## DDP:SystemComponentPartOfSystemComponent (SpecIF:TermStatementClass)
- dcterms:description: Superior element
- SpecIF:LocalTerm: (SystemComponent) PartOf (SystemComponent)
- SpecIF:TermStatus: SpecIF:LifecycleStatusReleased
- SpecIF:Domain: SpecIF:DomainSystemsEngineering
- SpecIF:Instantiation: SpecIF:InstantiationAuto, SpecIF:InstantiationUser

## DDP:SystemComponentSpecialismOfSystemComponent (SpecIF:TermStatementClass)
- dcterms:description: More generic item
- SpecIF:LocalTerm: (SystemComponent) SpecialismOf (SystemComponent)
- SpecIF:TermStatus: SpecIF:LifecycleStatusReleased
- SpecIF:Domain: SpecIF:DomainSystemsEngineering
- SpecIF:Instantiation: SpecIF:InstantiationAuto, SpecIF:InstantiationUser

## DDP:SystemComponentRelatesToRevision (SpecIF:TermStatementClass)
- dcterms:description: Relation to a version
- SpecIF:LocalTerm: (SystemComponent) RelatesTo (Revision)
- SpecIF:TermStatus: SpecIF:LifecycleStatusReleased
- SpecIF:Domain: SpecIF:DomainSystemsEngineering
- SpecIF:Instantiation: SpecIF:InstantiationAuto, SpecIF:InstantiationUser

## DDP:SystemComponentRelatesToConfiguration (SpecIF:TermStatementClass)
- dcterms:description: Relation to a configuration
- SpecIF:LocalTerm: (SystemComponent) RelatesTo (Configuration)
- SpecIF:TermStatus: SpecIF:LifecycleStatusReleased
- SpecIF:Domain: SpecIF:DomainSystemsEngineering
- SpecIF:Instantiation: SpecIF:InstantiationAuto, SpecIF:InstantiationUser

## DDP:SystemComponentOwnedByPerson (SpecIF:TermStatementClass)
- dcterms:description: The role owning this use case
- SpecIF:LocalTerm: (SystemComponent) OwnedBy (Person)
- SpecIF:TermStatus: SpecIF:LifecycleStatusReleased
- SpecIF:Domain: SpecIF:DomainSystemsEngineering
- SpecIF:Instantiation: SpecIF:InstantiationAuto, SpecIF:InstantiationUser

## DDP:SystemComponentImplementsProductFunction (SpecIF:TermStatementClass)
- dcterms:description: Function implemented by the component
- SpecIF:LocalTerm: (SystemComponent) Implements (ProductFunction)
- SpecIF:TermStatus: SpecIF:LifecycleStatusReleased
- SpecIF:Domain: SpecIF:DomainSystemsEngineering
- SpecIF:Instantiation: SpecIF:InstantiationAuto, SpecIF:InstantiationUser

## DDP:SystemComponentFulfilsRequirement (SpecIF:TermStatementClass)
- dcterms:description: Requirement implemented by the component. According to systems engineering best-practice, a requirement should first be answered by a function, and the function will be implemented by a component. This direct relation should therefore only be used if no functions have been defined.
- SpecIF:LocalTerm: (SystemComponent) Fulfils (Requirement)
- SpecIF:TermStatus: SpecIF:LifecycleStatusReleased
- SpecIF:Domain: SpecIF:DomainSystemsEngineering
- SpecIF:Instantiation: SpecIF:InstantiationAuto, SpecIF:InstantiationUser

## DDP:ComponentInterfaceAllocatedToSystemComponent (SpecIF:TermStatementClass)
- dcterms:description: System component this component Interface is allocated to
- SpecIF:LocalTerm: (ComponentInterface) AllocatedTo (SystemComponent)
- SpecIF:TermStatus: SpecIF:LifecycleStatusReleased
- SpecIF:Domain: SpecIF:DomainSystemsEngineering
- SpecIF:Instantiation: SpecIF:InstantiationAuto, SpecIF:InstantiationUser

## DDP:ComponentConnectionRelatesToConfiguration (SpecIF:TermStatementClass)
- dcterms:description: Relation to a configuration
- SpecIF:LocalTerm: (ComponentConnection) RelatesTo (Configuration)
- SpecIF:TermStatus: SpecIF:LifecycleStatusReleased
- SpecIF:Domain: SpecIF:DomainSystemsEngineering
- SpecIF:Instantiation: SpecIF:InstantiationAuto, SpecIF:InstantiationUser

## DDP:ComponentConnectionConnectsSystemComponent (SpecIF:TermStatementClass)
- dcterms:description: Represents the system components connected by this component connection.
- SpecIF:LocalTerm: (ComponentConnection) Connects (SystemComponent)
- SpecIF:TermStatus: SpecIF:LifecycleStatusReleased
- SpecIF:Domain: SpecIF:DomainSystemsEngineering
- SpecIF:Instantiation: SpecIF:InstantiationAuto, SpecIF:InstantiationUser

## DDP:ComponentStatePartOfComponentState (SpecIF:TermStatementClass)
- dcterms:description: Superior element
- SpecIF:LocalTerm: (ComponentState) PartOf (ComponentState)
- SpecIF:TermStatus: SpecIF:LifecycleStatusReleased
- SpecIF:Domain: SpecIF:DomainSystemsEngineering
- SpecIF:Instantiation: SpecIF:InstantiationAuto, SpecIF:InstantiationUser

## DDP:ComponentStateAllocatedToSystemComponent (SpecIF:TermStatementClass)
- dcterms:description: System component this component state is allocated to
- SpecIF:LocalTerm: (ComponentState) AllocatedTo (SystemComponent)
- SpecIF:TermStatus: SpecIF:LifecycleStatusReleased
- SpecIF:Domain: SpecIF:DomainSystemsEngineering
- SpecIF:Instantiation: SpecIF:InstantiationAuto, SpecIF:InstantiationUser

## DDP:ComponentStateChangesToComponentState (SpecIF:TermStatementClass)
- dcterms:description: Target state that is reached starting from an initial state
- SpecIF:LocalTerm: (ComponentState) ChangesTo (ComponentState)
- SpecIF:TermStatus: SpecIF:LifecycleStatusReleased
- SpecIF:Domain: SpecIF:DomainSystemsEngineering
- SpecIF:Instantiation: SpecIF:InstantiationAuto, SpecIF:InstantiationUser

## DDP:MechanicalComponentPartOfMechanicalComponent (SpecIF:TermStatementClass)
- dcterms:description: Superior element
- SpecIF:LocalTerm: (MechanicalComponent) PartOf (MechanicalComponent)
- SpecIF:TermStatus: SpecIF:LifecycleStatusReleased
- SpecIF:Domain: SpecIF:DomainSystemsEngineering
- SpecIF:Instantiation: SpecIF:InstantiationAuto, SpecIF:InstantiationUser

## DDP:MechanicalComponentSpecialismOfMechanicalComponent (SpecIF:TermStatementClass)
- dcterms:description: More generic item
- SpecIF:LocalTerm: (MechanicalComponent) SpecialismOf (MechanicalComponent)
- SpecIF:TermStatus: SpecIF:LifecycleStatusReleased
- SpecIF:Domain: SpecIF:DomainSystemsEngineering
- SpecIF:Instantiation: SpecIF:InstantiationAuto, SpecIF:InstantiationUser

## DDP:MechanicalComponentRelatesToRevision (SpecIF:TermStatementClass)
- dcterms:description: Relation to a version
- SpecIF:LocalTerm: (MechanicalComponent) RelatesTo (Revision)
- SpecIF:TermStatus: SpecIF:LifecycleStatusReleased
- SpecIF:Domain: SpecIF:DomainSystemsEngineering
- SpecIF:Instantiation: SpecIF:InstantiationAuto, SpecIF:InstantiationUser

## DDP:MechanicalComponentRelatesToConfiguration (SpecIF:TermStatementClass)
- dcterms:description: Relation to a configuration
- SpecIF:LocalTerm: (MechanicalComponent) RelatesTo (Configuration)
- SpecIF:TermStatus: SpecIF:LifecycleStatusReleased
- SpecIF:Domain: SpecIF:DomainSystemsEngineering
- SpecIF:Instantiation: SpecIF:InstantiationAuto, SpecIF:InstantiationUser

## DDP:MechanicalComponentOwnedByPerson (SpecIF:TermStatementClass)
- dcterms:description: The role owning this use case
- SpecIF:LocalTerm: (MechanicalComponent) OwnedBy (Person)
- SpecIF:TermStatus: SpecIF:LifecycleStatusReleased
- SpecIF:Domain: SpecIF:DomainSystemsEngineering
- SpecIF:Instantiation: SpecIF:InstantiationAuto, SpecIF:InstantiationUser

## DDP:MechanicalComponentImplementsProductFunction (SpecIF:TermStatementClass)
- dcterms:description: Function implemented by the component
- SpecIF:LocalTerm: (MechanicalComponent) Implements (ProductFunction)
- SpecIF:TermStatus: SpecIF:LifecycleStatusReleased
- SpecIF:Domain: SpecIF:DomainSystemsEngineering
- SpecIF:Instantiation: SpecIF:InstantiationAuto, SpecIF:InstantiationUser

## DDP:MechanicalComponentFulfilsRequirement (SpecIF:TermStatementClass)
- dcterms:description: Requirement implemented by the component. According to systems engineering best-practice, a requirement should first be answered by a function, and the function will be implemented by a component. This direct relation should therefore only be used if no functions have been defined.
- SpecIF:LocalTerm: (MechanicalComponent) Fulfils (Requirement)
- SpecIF:TermStatus: SpecIF:LifecycleStatusReleased
- SpecIF:Domain: SpecIF:DomainSystemsEngineering
- SpecIF:Instantiation: SpecIF:InstantiationAuto, SpecIF:InstantiationUser

## DDP:MechanicalComponentMadeOfMaterial (SpecIF:TermStatementClass)
- dcterms:description: Material assigned to the mechanical component
- SpecIF:LocalTerm: (MechanicalComponent) MadeOf (Material)
- SpecIF:TermStatus: SpecIF:LifecycleStatusReleased
- SpecIF:Domain: SpecIF:DomainSystemsEngineering
- SpecIF:Instantiation: SpecIF:InstantiationAuto, SpecIF:InstantiationUser

## DDP:MechanicalComponentInstanceAllocatedToMechanicalComponent (SpecIF:TermStatementClass)
- dcterms:description: Mechanical component this component instance is defined in
- SpecIF:LocalTerm: (MechanicalComponentInstance) AllocatedTo (MechanicalComponent)
- SpecIF:TermStatus: SpecIF:LifecycleStatusReleased
- SpecIF:Domain: SpecIF:DomainSystemsEngineering
- SpecIF:Instantiation: SpecIF:InstantiationAuto, SpecIF:InstantiationUser

## DDP:MechanicalComponentInstanceInstancesMechanicalComponent (SpecIF:TermStatementClass)
- dcterms:description: Mechanical component this instance refers to. The concept of component instances refering to components is essential to mechanical CAD and PDM and implemented in all relevant standards.
- SpecIF:LocalTerm: (MechanicalComponentInstance) Instances (MechanicalComponent)
- SpecIF:TermStatus: SpecIF:LifecycleStatusReleased
- SpecIF:Domain: SpecIF:DomainSystemsEngineering
- SpecIF:Instantiation: SpecIF:InstantiationAuto, SpecIF:InstantiationUser

## DDP:MaterialSpecialismOfMaterial (SpecIF:TermStatementClass)
- dcterms:description: More generic item
- SpecIF:LocalTerm: (Material) SpecialismOf (Material)
- SpecIF:TermStatus: SpecIF:LifecycleStatusReleased
- SpecIF:Domain: SpecIF:DomainSystemsEngineering
- SpecIF:Instantiation: SpecIF:InstantiationAuto, SpecIF:InstantiationUser

## DDP:ModelViewRelatesToConfiguration (SpecIF:TermStatementClass)
- dcterms:description: Relation to a configuration
- SpecIF:LocalTerm: (ModelView) RelatesTo (Configuration)
- SpecIF:TermStatus: SpecIF:LifecycleStatusReleased
- SpecIF:Domain: SpecIF:DomainSystemsEngineering
- SpecIF:Instantiation: SpecIF:InstantiationAuto, SpecIF:InstantiationUser

## DDP:ModelViewAllocatedToMechanicalComponent (SpecIF:TermStatementClass)
- dcterms:description: Mechanical component this model view is allocated to
- SpecIF:LocalTerm: (ModelView) AllocatedTo (MechanicalComponent)
- SpecIF:TermStatus: SpecIF:LifecycleStatusReleased
- SpecIF:Domain: SpecIF:DomainSystemsEngineering
- SpecIF:Instantiation: SpecIF:InstantiationAuto, SpecIF:InstantiationUser

## DDP:ModelAnnotationAllocatedToModelView (SpecIF:TermStatementClass)
- dcterms:description: Model view this model annotation is allocated to
- SpecIF:LocalTerm: (ModelAnnotation) AllocatedTo (ModelView)
- SpecIF:TermStatus: SpecIF:LifecycleStatusReleased
- SpecIF:Domain: SpecIF:DomainSystemsEngineering
- SpecIF:Instantiation: SpecIF:InstantiationAuto, SpecIF:InstantiationUser

## DDP:ModelAnnotationRelatesToModelAnnotation (SpecIF:TermStatementClass)
- dcterms:description: Related annotations, i. e. datums
- SpecIF:LocalTerm: (ModelAnnotation) RelatesTo (ModelAnnotation)
- SpecIF:TermStatus: SpecIF:LifecycleStatusReleased
- SpecIF:Domain: SpecIF:DomainSystemsEngineering
- SpecIF:Instantiation: SpecIF:InstantiationAuto, SpecIF:InstantiationUser

## DDP:KinematicMechanismAllocatedToMechanicalComponent (SpecIF:TermStatementClass)
- dcterms:description: Mechanical component this kinematic mechanism is allocated to
- SpecIF:LocalTerm: (KinematicMechanism) AllocatedTo (MechanicalComponent)
- SpecIF:TermStatus: SpecIF:LifecycleStatusReleased
- SpecIF:Domain: SpecIF:DomainSystemsEngineering
- SpecIF:Instantiation: SpecIF:InstantiationAuto, SpecIF:InstantiationUser

## DDP:KinematicJointRelatesToConfiguration (SpecIF:TermStatementClass)
- dcterms:description: Relation to a configuration
- SpecIF:LocalTerm: (KinematicJoint) RelatesTo (Configuration)
- SpecIF:TermStatus: SpecIF:LifecycleStatusReleased
- SpecIF:Domain: SpecIF:DomainSystemsEngineering
- SpecIF:Instantiation: SpecIF:InstantiationAuto, SpecIF:InstantiationUser

## DDP:KinematicJointConnectsSystemComponent (SpecIF:TermStatementClass)
- dcterms:description: Represents the system components connected by this component connection.
- SpecIF:LocalTerm: (KinematicJoint) Connects (SystemComponent)
- SpecIF:TermStatus: SpecIF:LifecycleStatusReleased
- SpecIF:Domain: SpecIF:DomainSystemsEngineering
- SpecIF:Instantiation: SpecIF:InstantiationAuto, SpecIF:InstantiationUser

## DDP:KinematicJointConnectsMechanicalComponent (SpecIF:TermStatementClass)
- dcterms:description: Connected parts
- SpecIF:LocalTerm: (KinematicJoint) Connects (MechanicalComponent)
- SpecIF:TermStatus: SpecIF:LifecycleStatusReleased
- SpecIF:Domain: SpecIF:DomainSystemsEngineering
- SpecIF:Instantiation: SpecIF:InstantiationAuto, SpecIF:InstantiationUser

## DDP:KinematicJointAllocatedToKinematicMechanism (SpecIF:TermStatementClass)
- dcterms:description: Kinematic mechanism this joint is allocated to
- SpecIF:LocalTerm: (KinematicJoint) AllocatedTo (KinematicMechanism)
- SpecIF:TermStatus: SpecIF:LifecycleStatusReleased
- SpecIF:Domain: SpecIF:DomainSystemsEngineering
- SpecIF:Instantiation: SpecIF:InstantiationAuto, SpecIF:InstantiationUser

## DDP:KinematicJointObservedByKinematicSensor (SpecIF:TermStatementClass)
- dcterms:description: Kinematic sensor observing this kinematic joint
- SpecIF:LocalTerm: (KinematicJoint) ObservedBy (KinematicSensor)
- SpecIF:TermStatus: SpecIF:LifecycleStatusReleased
- SpecIF:Domain: SpecIF:DomainSystemsEngineering
- SpecIF:Instantiation: SpecIF:InstantiationAuto, SpecIF:InstantiationUser

## DDP:KinematicSensorAllocatedToKinematicMechanism (SpecIF:TermStatementClass)
- dcterms:description: Kinematic mechanism this sensor is allocated to
- SpecIF:LocalTerm: (KinematicSensor) AllocatedTo (KinematicMechanism)
- SpecIF:TermStatus: SpecIF:LifecycleStatusReleased
- SpecIF:Domain: SpecIF:DomainSystemsEngineering
- SpecIF:Instantiation: SpecIF:InstantiationAuto, SpecIF:InstantiationUser

## DDP:KinematicMotionInvolvesMechanicalComponent (SpecIF:TermStatementClass)
- dcterms:description: Components involved by the kinematic motion
- SpecIF:LocalTerm: (KinematicMotion) Involves (MechanicalComponent)
- SpecIF:TermStatus: SpecIF:LifecycleStatusReleased
- SpecIF:Domain: SpecIF:DomainSystemsEngineering
- SpecIF:Instantiation: SpecIF:InstantiationAuto, SpecIF:InstantiationUser

## DDP:JoiningProcessSpecialismOfJoiningProcess (SpecIF:TermStatementClass)
- dcterms:description: More generic item
- SpecIF:LocalTerm: (JoiningProcess) SpecialismOf (JoiningProcess)
- SpecIF:TermStatus: SpecIF:LifecycleStatusReleased
- SpecIF:Domain: SpecIF:DomainSystemsEngineering
- SpecIF:Instantiation: SpecIF:InstantiationAuto, SpecIF:InstantiationUser

## DDP:JoiningElementRelatesToConfiguration (SpecIF:TermStatementClass)
- dcterms:description: Relation to a configuration
- SpecIF:LocalTerm: (JoiningElement) RelatesTo (Configuration)
- SpecIF:TermStatus: SpecIF:LifecycleStatusReleased
- SpecIF:Domain: SpecIF:DomainSystemsEngineering
- SpecIF:Instantiation: SpecIF:InstantiationAuto, SpecIF:InstantiationUser

## DDP:JoiningElementConnectsSystemComponent (SpecIF:TermStatementClass)
- dcterms:description: Represents the system components connected by this component connection.
- SpecIF:LocalTerm: (JoiningElement) Connects (SystemComponent)
- SpecIF:TermStatus: SpecIF:LifecycleStatusReleased
- SpecIF:Domain: SpecIF:DomainSystemsEngineering
- SpecIF:Instantiation: SpecIF:InstantiationAuto, SpecIF:InstantiationUser

## DDP:JoiningElementConnectsMechanicalComponentInstance (SpecIF:TermStatementClass)
- dcterms:description: Mechanical component instances connected by this joining element
- SpecIF:LocalTerm: (JoiningElement) Connects (MechanicalComponentInstance)
- SpecIF:TermStatus: SpecIF:LifecycleStatusReleased
- SpecIF:Domain: SpecIF:DomainSystemsEngineering
- SpecIF:Instantiation: SpecIF:InstantiationAuto, SpecIF:InstantiationUser

## DDP:JoiningElementAllocatedToMechanicalComponent (SpecIF:TermStatementClass)
- dcterms:description: Mechanical component this joining element is allocated to
- SpecIF:LocalTerm: (JoiningElement) AllocatedTo (MechanicalComponent)
- SpecIF:TermStatus: SpecIF:LifecycleStatusReleased
- SpecIF:Domain: SpecIF:DomainSystemsEngineering
- SpecIF:Instantiation: SpecIF:InstantiationAuto, SpecIF:InstantiationUser

## DDP:JoiningElementAppliesJoiningProcess (SpecIF:TermStatementClass)
- dcterms:description: Joining process used for this joining element
- SpecIF:LocalTerm: (JoiningElement) Applies (JoiningProcess)
- SpecIF:TermStatus: SpecIF:LifecycleStatusReleased
- SpecIF:Domain: SpecIF:DomainSystemsEngineering
- SpecIF:Instantiation: SpecIF:InstantiationAuto, SpecIF:InstantiationUser

## DDP:ElectricElectronicComponentPartOfElectricElectronicComponent (SpecIF:TermStatementClass)
- dcterms:description: Superior element
- SpecIF:LocalTerm: (ElectricElectronicComponent) PartOf (ElectricElectronicComponent)
- SpecIF:TermStatus: SpecIF:LifecycleStatusReleased
- SpecIF:Domain: SpecIF:DomainSystemsEngineering
- SpecIF:Instantiation: SpecIF:InstantiationAuto, SpecIF:InstantiationUser

## DDP:ElectricElectronicComponentSpecialismOfElectricElectronicComponent (SpecIF:TermStatementClass)
- dcterms:description: More generic item
- SpecIF:LocalTerm: (ElectricElectronicComponent) SpecialismOf (ElectricElectronicComponent)
- SpecIF:TermStatus: SpecIF:LifecycleStatusReleased
- SpecIF:Domain: SpecIF:DomainSystemsEngineering
- SpecIF:Instantiation: SpecIF:InstantiationAuto, SpecIF:InstantiationUser

## DDP:ElectricElectronicComponentRelatesToRevision (SpecIF:TermStatementClass)
- dcterms:description: Relation to a version
- SpecIF:LocalTerm: (ElectricElectronicComponent) RelatesTo (Revision)
- SpecIF:TermStatus: SpecIF:LifecycleStatusReleased
- SpecIF:Domain: SpecIF:DomainSystemsEngineering
- SpecIF:Instantiation: SpecIF:InstantiationAuto, SpecIF:InstantiationUser

## DDP:ElectricElectronicComponentRelatesToConfiguration (SpecIF:TermStatementClass)
- dcterms:description: Relation to a configuration
- SpecIF:LocalTerm: (ElectricElectronicComponent) RelatesTo (Configuration)
- SpecIF:TermStatus: SpecIF:LifecycleStatusReleased
- SpecIF:Domain: SpecIF:DomainSystemsEngineering
- SpecIF:Instantiation: SpecIF:InstantiationAuto, SpecIF:InstantiationUser

## DDP:ElectricElectronicComponentOwnedByPerson (SpecIF:TermStatementClass)
- dcterms:description: The role owning this use case
- SpecIF:LocalTerm: (ElectricElectronicComponent) OwnedBy (Person)
- SpecIF:TermStatus: SpecIF:LifecycleStatusReleased
- SpecIF:Domain: SpecIF:DomainSystemsEngineering
- SpecIF:Instantiation: SpecIF:InstantiationAuto, SpecIF:InstantiationUser

## DDP:ElectricElectronicComponentImplementsProductFunction (SpecIF:TermStatementClass)
- dcterms:description: Function implemented by the component
- SpecIF:LocalTerm: (ElectricElectronicComponent) Implements (ProductFunction)
- SpecIF:TermStatus: SpecIF:LifecycleStatusReleased
- SpecIF:Domain: SpecIF:DomainSystemsEngineering
- SpecIF:Instantiation: SpecIF:InstantiationAuto, SpecIF:InstantiationUser

## DDP:ElectricElectronicComponentFulfilsRequirement (SpecIF:TermStatementClass)
- dcterms:description: Requirement implemented by the component. According to systems engineering best-practice, a requirement should first be answered by a function, and the function will be implemented by a component. This direct relation should therefore only be used if no functions have been defined.
- SpecIF:LocalTerm: (ElectricElectronicComponent) Fulfils (Requirement)
- SpecIF:TermStatus: SpecIF:LifecycleStatusReleased
- SpecIF:Domain: SpecIF:DomainSystemsEngineering
- SpecIF:Instantiation: SpecIF:InstantiationAuto, SpecIF:InstantiationUser

## DDP:ElectricElectronicComponentRelatesToMechanicalComponent (SpecIF:TermStatementClass)
- dcterms:description: Mechanical component this electric/electronic component relates to
- SpecIF:LocalTerm: (ElectricElectronicComponent) RelatesTo (MechanicalComponent)
- SpecIF:TermStatus: SpecIF:LifecycleStatusReleased
- SpecIF:Domain: SpecIF:DomainSystemsEngineering
- SpecIF:Instantiation: SpecIF:InstantiationAuto, SpecIF:InstantiationUser

## DDP:ElectricElectronicPortAllocatedToSystemComponent (SpecIF:TermStatementClass)
- dcterms:description: System component this component Interface is allocated to
- SpecIF:LocalTerm: (ElectricElectronicPort) AllocatedTo (SystemComponent)
- SpecIF:TermStatus: SpecIF:LifecycleStatusReleased
- SpecIF:Domain: SpecIF:DomainSystemsEngineering
- SpecIF:Instantiation: SpecIF:InstantiationAuto, SpecIF:InstantiationUser

## DDP:ElectricElectronicConnectionRelatesToConfiguration (SpecIF:TermStatementClass)
- dcterms:description: Relation to a configuration
- SpecIF:LocalTerm: (ElectricElectronicConnection) RelatesTo (Configuration)
- SpecIF:TermStatus: SpecIF:LifecycleStatusReleased
- SpecIF:Domain: SpecIF:DomainSystemsEngineering
- SpecIF:Instantiation: SpecIF:InstantiationAuto, SpecIF:InstantiationUser

## DDP:ElectricElectronicConnectionConnectsSystemComponent (SpecIF:TermStatementClass)
- dcterms:description: Represents the system components connected by this component connection.
- SpecIF:LocalTerm: (ElectricElectronicConnection) Connects (SystemComponent)
- SpecIF:TermStatus: SpecIF:LifecycleStatusReleased
- SpecIF:Domain: SpecIF:DomainSystemsEngineering
- SpecIF:Instantiation: SpecIF:InstantiationAuto, SpecIF:InstantiationUser

## DDP:ElectricElectronicConnectionConnectsElectricElectronicComponent (SpecIF:TermStatementClass)
- dcterms:description: Electric/electronic component instances connected by this joining element
- SpecIF:LocalTerm: (ElectricElectronicConnection) Connects (ElectricElectronicComponent)
- SpecIF:TermStatus: SpecIF:LifecycleStatusReleased
- SpecIF:Domain: SpecIF:DomainSystemsEngineering
- SpecIF:Instantiation: SpecIF:InstantiationAuto, SpecIF:InstantiationUser

## DDP:SoftwareClassPartOfSoftwareClass (SpecIF:TermStatementClass)
- dcterms:description: Superior element
- SpecIF:LocalTerm: (SoftwareClass) PartOf (SoftwareClass)
- SpecIF:TermStatus: SpecIF:LifecycleStatusReleased
- SpecIF:Domain: SpecIF:DomainSystemsEngineering
- SpecIF:Instantiation: SpecIF:InstantiationAuto, SpecIF:InstantiationUser

## DDP:SoftwareClassSpecialismOfSoftwareClass (SpecIF:TermStatementClass)
- dcterms:description: More generic item
- SpecIF:LocalTerm: (SoftwareClass) SpecialismOf (SoftwareClass)
- SpecIF:TermStatus: SpecIF:LifecycleStatusReleased
- SpecIF:Domain: SpecIF:DomainSystemsEngineering
- SpecIF:Instantiation: SpecIF:InstantiationAuto, SpecIF:InstantiationUser

## DDP:SoftwareClassRelatesToRevision (SpecIF:TermStatementClass)
- dcterms:description: Relation to a version
- SpecIF:LocalTerm: (SoftwareClass) RelatesTo (Revision)
- SpecIF:TermStatus: SpecIF:LifecycleStatusReleased
- SpecIF:Domain: SpecIF:DomainSystemsEngineering
- SpecIF:Instantiation: SpecIF:InstantiationAuto, SpecIF:InstantiationUser

## DDP:SoftwareClassRelatesToConfiguration (SpecIF:TermStatementClass)
- dcterms:description: Relation to a configuration
- SpecIF:LocalTerm: (SoftwareClass) RelatesTo (Configuration)
- SpecIF:TermStatus: SpecIF:LifecycleStatusReleased
- SpecIF:Domain: SpecIF:DomainSystemsEngineering
- SpecIF:Instantiation: SpecIF:InstantiationAuto, SpecIF:InstantiationUser

## DDP:SoftwareClassOwnedByPerson (SpecIF:TermStatementClass)
- dcterms:description: The role owning this use case
- SpecIF:LocalTerm: (SoftwareClass) OwnedBy (Person)
- SpecIF:TermStatus: SpecIF:LifecycleStatusReleased
- SpecIF:Domain: SpecIF:DomainSystemsEngineering
- SpecIF:Instantiation: SpecIF:InstantiationAuto, SpecIF:InstantiationUser

## DDP:SoftwareClassImplementsProductFunction (SpecIF:TermStatementClass)
- dcterms:description: Function implemented by the component
- SpecIF:LocalTerm: (SoftwareClass) Implements (ProductFunction)
- SpecIF:TermStatus: SpecIF:LifecycleStatusReleased
- SpecIF:Domain: SpecIF:DomainSystemsEngineering
- SpecIF:Instantiation: SpecIF:InstantiationAuto, SpecIF:InstantiationUser

## DDP:SoftwareClassFulfilsRequirement (SpecIF:TermStatementClass)
- dcterms:description: Requirement implemented by the component. According to systems engineering best-practice, a requirement should first be answered by a function, and the function will be implemented by a component. This direct relation should therefore only be used if no functions have been defined.
- SpecIF:LocalTerm: (SoftwareClass) Fulfils (Requirement)
- SpecIF:TermStatus: SpecIF:LifecycleStatusReleased
- SpecIF:Domain: SpecIF:DomainSystemsEngineering
- SpecIF:Instantiation: SpecIF:InstantiationAuto, SpecIF:InstantiationUser

## DDP:SoftwareInterfaceAllocatedToSystemComponent (SpecIF:TermStatementClass)
- dcterms:description: System component this component Interface is allocated to
- SpecIF:LocalTerm: (SoftwareInterface) AllocatedTo (SystemComponent)
- SpecIF:TermStatus: SpecIF:LifecycleStatusReleased
- SpecIF:Domain: SpecIF:DomainSystemsEngineering
- SpecIF:Instantiation: SpecIF:InstantiationAuto, SpecIF:InstantiationUser

## DDP:SoftwareInterfaceAllocatedToSoftwareComponent (SpecIF:TermStatementClass)
- dcterms:description: Software class this interface is allocated to
- SpecIF:LocalTerm: (SoftwareInterface) AllocatedTo (SoftwareComponent)
- SpecIF:TermStatus: SpecIF:LifecycleStatusReleased
- SpecIF:Domain: SpecIF:DomainSystemsEngineering
- SpecIF:Instantiation: SpecIF:InstantiationAuto, SpecIF:InstantiationUser

## DDP:SoftwareComponentPartOfSoftwareComponent (SpecIF:TermStatementClass)
- dcterms:description: Superior element
- SpecIF:LocalTerm: (SoftwareComponent) PartOf (SoftwareComponent)
- SpecIF:TermStatus: SpecIF:LifecycleStatusReleased
- SpecIF:Domain: SpecIF:DomainSystemsEngineering
- SpecIF:Instantiation: SpecIF:InstantiationAuto, SpecIF:InstantiationUser

## DDP:SoftwareComponentSpecialismOfSoftwareComponent (SpecIF:TermStatementClass)
- dcterms:description: More generic item
- SpecIF:LocalTerm: (SoftwareComponent) SpecialismOf (SoftwareComponent)
- SpecIF:TermStatus: SpecIF:LifecycleStatusReleased
- SpecIF:Domain: SpecIF:DomainSystemsEngineering
- SpecIF:Instantiation: SpecIF:InstantiationAuto, SpecIF:InstantiationUser

## DDP:SoftwareComponentRelatesToRevision (SpecIF:TermStatementClass)
- dcterms:description: Relation to a version
- SpecIF:LocalTerm: (SoftwareComponent) RelatesTo (Revision)
- SpecIF:TermStatus: SpecIF:LifecycleStatusReleased
- SpecIF:Domain: SpecIF:DomainSystemsEngineering
- SpecIF:Instantiation: SpecIF:InstantiationAuto, SpecIF:InstantiationUser

## DDP:SoftwareComponentRelatesToConfiguration (SpecIF:TermStatementClass)
- dcterms:description: Relation to a configuration
- SpecIF:LocalTerm: (SoftwareComponent) RelatesTo (Configuration)
- SpecIF:TermStatus: SpecIF:LifecycleStatusReleased
- SpecIF:Domain: SpecIF:DomainSystemsEngineering
- SpecIF:Instantiation: SpecIF:InstantiationAuto, SpecIF:InstantiationUser

## DDP:SoftwareComponentOwnedByPerson (SpecIF:TermStatementClass)
- dcterms:description: The role owning this use case
- SpecIF:LocalTerm: (SoftwareComponent) OwnedBy (Person)
- SpecIF:TermStatus: SpecIF:LifecycleStatusReleased
- SpecIF:Domain: SpecIF:DomainSystemsEngineering
- SpecIF:Instantiation: SpecIF:InstantiationAuto, SpecIF:InstantiationUser

## DDP:SoftwareComponentImplementsProductFunction (SpecIF:TermStatementClass)
- dcterms:description: Function implemented by the component
- SpecIF:LocalTerm: (SoftwareComponent) Implements (ProductFunction)
- SpecIF:TermStatus: SpecIF:LifecycleStatusReleased
- SpecIF:Domain: SpecIF:DomainSystemsEngineering
- SpecIF:Instantiation: SpecIF:InstantiationAuto, SpecIF:InstantiationUser

## DDP:SoftwareComponentFulfilsRequirement (SpecIF:TermStatementClass)
- dcterms:description: Requirement implemented by the component. According to systems engineering best-practice, a requirement should first be answered by a function, and the function will be implemented by a component. This direct relation should therefore only be used if no functions have been defined.
- SpecIF:LocalTerm: (SoftwareComponent) Fulfils (Requirement)
- SpecIF:TermStatus: SpecIF:LifecycleStatusReleased
- SpecIF:Domain: SpecIF:DomainSystemsEngineering
- SpecIF:Instantiation: SpecIF:InstantiationAuto, SpecIF:InstantiationUser

## DDP:HydraulicPneumaticPortAllocatedToSystemComponent (SpecIF:TermStatementClass)
- dcterms:description: System component this component Interface is allocated to
- SpecIF:LocalTerm: (HydraulicPneumaticPort) AllocatedTo (SystemComponent)
- SpecIF:TermStatus: SpecIF:LifecycleStatusReleased
- SpecIF:Domain: SpecIF:DomainSystemsEngineering
- SpecIF:Instantiation: SpecIF:InstantiationAuto, SpecIF:InstantiationUser

## DDP:ValidationPlanPartOfValidationPlan (SpecIF:TermStatementClass)
- dcterms:description: Superior element
- SpecIF:LocalTerm: (ValidationPlan) PartOf (ValidationPlan)
- SpecIF:TermStatus: SpecIF:LifecycleStatusReleased
- SpecIF:Domain: SpecIF:DomainSystemsEngineering
- SpecIF:Instantiation: SpecIF:InstantiationAuto, SpecIF:InstantiationUser

## DDP:ValidationBoundaryConditionPartOfValidationBoundaryCondition (SpecIF:TermStatementClass)
- dcterms:description: Superior element
- SpecIF:LocalTerm: (ValidationBoundaryCondition) PartOf (ValidationBoundaryCondition)
- SpecIF:TermStatus: SpecIF:LifecycleStatusReleased
- SpecIF:Domain: SpecIF:DomainSystemsEngineering
- SpecIF:Instantiation: SpecIF:InstantiationAuto, SpecIF:InstantiationUser

## DDP:ValidationRunPartOfValidationRun (SpecIF:TermStatementClass)
- dcterms:description: Superior element
- SpecIF:LocalTerm: (ValidationRun) PartOf (ValidationRun)
- SpecIF:TermStatus: SpecIF:LifecycleStatusReleased
- SpecIF:Domain: SpecIF:DomainSystemsEngineering
- SpecIF:Instantiation: SpecIF:InstantiationAuto, SpecIF:InstantiationUser

## DDP:ValidationResultPartOfValidationResult (SpecIF:TermStatementClass)
- dcterms:description: Superior element
- SpecIF:LocalTerm: (ValidationResult) PartOf (ValidationResult)
- SpecIF:TermStatus: SpecIF:LifecycleStatusReleased
- SpecIF:Domain: SpecIF:DomainSystemsEngineering
- SpecIF:Instantiation: SpecIF:InstantiationAuto, SpecIF:InstantiationUser

## DDP:ManufacturingOperationPartOfManufacturingOperation (SpecIF:TermStatementClass)
- dcterms:description: Superior element
- SpecIF:LocalTerm: (ManufacturingOperation) PartOf (ManufacturingOperation)
- SpecIF:TermStatus: SpecIF:LifecycleStatusReleased
- SpecIF:Domain: SpecIF:DomainSystemsEngineering
- SpecIF:Instantiation: SpecIF:InstantiationAuto, SpecIF:InstantiationUser

## DDP:ManufacturingOperationInContextOfMechanicalComponent (SpecIF:TermStatementClass)
- dcterms:description: Represents a mechanical component this manufacturing operation is in context of
- SpecIF:LocalTerm: (ManufacturingOperation) InContextOf (MechanicalComponent)
- SpecIF:TermStatus: SpecIF:LifecycleStatusReleased
- SpecIF:Domain: SpecIF:DomainSystemsEngineering
- SpecIF:Instantiation: SpecIF:InstantiationAuto, SpecIF:InstantiationUser

## DDP:ManufacturingOperationAppliesToMechanicalComponentInstance (SpecIF:TermStatementClass)
- dcterms:description: The specific mechanical or electrical component instances the manufacturing operation applies to.
- SpecIF:LocalTerm: (ManufacturingOperation) AppliesTo (MechanicalComponentInstance)
- SpecIF:TermStatus: SpecIF:LifecycleStatusReleased
- SpecIF:Domain: SpecIF:DomainSystemsEngineering
- SpecIF:Instantiation: SpecIF:InstantiationAuto, SpecIF:InstantiationUser

## DDP:ManufacturingOperationPerformedUsingManufacturingEquipmentComponent (SpecIF:TermStatementClass)
- dcterms:description: Any tools and fixtures used to perform the manufacturing operation.
- SpecIF:LocalTerm: (ManufacturingOperation) PerformedUsing (ManufacturingEquipmentComponent)
- SpecIF:TermStatus: SpecIF:LifecycleStatusReleased
- SpecIF:Domain: SpecIF:DomainSystemsEngineering
- SpecIF:Instantiation: SpecIF:InstantiationAuto, SpecIF:InstantiationUser

## DDP:ManufacturingEquipmentComponentPartOfManufacturingEquipmentComponent (SpecIF:TermStatementClass)
- dcterms:description: Superior element
- SpecIF:LocalTerm: (ManufacturingEquipmentComponent) PartOf (ManufacturingEquipmentComponent)
- SpecIF:TermStatus: SpecIF:LifecycleStatusReleased
- SpecIF:Domain: SpecIF:DomainSystemsEngineering
- SpecIF:Instantiation: SpecIF:InstantiationAuto, SpecIF:InstantiationUser

## DDP:ManufacturingEquipmentComponentSpecialismOfManufacturingEquipmentComponent (SpecIF:TermStatementClass)
- dcterms:description: More generic item
- SpecIF:LocalTerm: (ManufacturingEquipmentComponent) SpecialismOf (ManufacturingEquipmentComponent)
- SpecIF:TermStatus: SpecIF:LifecycleStatusReleased
- SpecIF:Domain: SpecIF:DomainSystemsEngineering
- SpecIF:Instantiation: SpecIF:InstantiationAuto, SpecIF:InstantiationUser

## DDP:ManufacturingEquipmentComponentRelatesToRevision (SpecIF:TermStatementClass)
- dcterms:description: Relation to a version
- SpecIF:LocalTerm: (ManufacturingEquipmentComponent) RelatesTo (Revision)
- SpecIF:TermStatus: SpecIF:LifecycleStatusReleased
- SpecIF:Domain: SpecIF:DomainSystemsEngineering
- SpecIF:Instantiation: SpecIF:InstantiationAuto, SpecIF:InstantiationUser

## DDP:ManufacturingEquipmentComponentRelatesToConfiguration (SpecIF:TermStatementClass)
- dcterms:description: Relation to a configuration
- SpecIF:LocalTerm: (ManufacturingEquipmentComponent) RelatesTo (Configuration)
- SpecIF:TermStatus: SpecIF:LifecycleStatusReleased
- SpecIF:Domain: SpecIF:DomainSystemsEngineering
- SpecIF:Instantiation: SpecIF:InstantiationAuto, SpecIF:InstantiationUser

## DDP:ManufacturingEquipmentComponentOwnedByPerson (SpecIF:TermStatementClass)
- dcterms:description: The role owning this use case
- SpecIF:LocalTerm: (ManufacturingEquipmentComponent) OwnedBy (Person)
- SpecIF:TermStatus: SpecIF:LifecycleStatusReleased
- SpecIF:Domain: SpecIF:DomainSystemsEngineering
- SpecIF:Instantiation: SpecIF:InstantiationAuto, SpecIF:InstantiationUser

## DDP:ManufacturingEquipmentComponentImplementsProductFunction (SpecIF:TermStatementClass)
- dcterms:description: Function implemented by the component
- SpecIF:LocalTerm: (ManufacturingEquipmentComponent) Implements (ProductFunction)
- SpecIF:TermStatus: SpecIF:LifecycleStatusReleased
- SpecIF:Domain: SpecIF:DomainSystemsEngineering
- SpecIF:Instantiation: SpecIF:InstantiationAuto, SpecIF:InstantiationUser

## DDP:ManufacturingEquipmentComponentFulfilsRequirement (SpecIF:TermStatementClass)
- dcterms:description: Requirement implemented by the component. According to systems engineering best-practice, a requirement should first be answered by a function, and the function will be implemented by a component. This direct relation should therefore only be used if no functions have been defined.
- SpecIF:LocalTerm: (ManufacturingEquipmentComponent) Fulfils (Requirement)
- SpecIF:TermStatus: SpecIF:LifecycleStatusReleased
- SpecIF:Domain: SpecIF:DomainSystemsEngineering
- SpecIF:Instantiation: SpecIF:InstantiationAuto, SpecIF:InstantiationUser

## DDP:ManufacturingEquipmentComponentMadeOfMaterial (SpecIF:TermStatementClass)
- dcterms:description: Material assigned to the mechanical component
- SpecIF:LocalTerm: (ManufacturingEquipmentComponent) MadeOf (Material)
- SpecIF:TermStatus: SpecIF:LifecycleStatusReleased
- SpecIF:Domain: SpecIF:DomainSystemsEngineering
- SpecIF:Instantiation: SpecIF:InstantiationAuto, SpecIF:InstantiationUser

## DDP:InspectionCharacteristicPartOfInspectionCharacteristic (SpecIF:TermStatementClass)
- dcterms:description: Superior element
- SpecIF:LocalTerm: (InspectionCharacteristic) PartOf (InspectionCharacteristic)
- SpecIF:TermStatus: SpecIF:LifecycleStatusReleased
- SpecIF:Domain: SpecIF:DomainSystemsEngineering
- SpecIF:Instantiation: SpecIF:InstantiationAuto, SpecIF:InstantiationUser

## DDP:InspectionCharacteristicAllocatedToInspectionPlan (SpecIF:TermStatementClass)
- dcterms:description: Inspection plan this characteristic is allocated to
- SpecIF:LocalTerm: (InspectionCharacteristic) AllocatedTo (InspectionPlan)
- SpecIF:TermStatus: SpecIF:LifecycleStatusReleased
- SpecIF:Domain: SpecIF:DomainSystemsEngineering
- SpecIF:Instantiation: SpecIF:InstantiationAuto, SpecIF:InstantiationUser

## DDP:InspectionCharacteristicValidatesProductFunction (SpecIF:TermStatementClass)
- dcterms:description: Product function this inspection characteristic is designed to verify
- SpecIF:LocalTerm: (InspectionCharacteristic) Validates (ProductFunction)
- SpecIF:TermStatus: SpecIF:LifecycleStatusReleased
- SpecIF:Domain: SpecIF:DomainSystemsEngineering
- SpecIF:Instantiation: SpecIF:InstantiationAuto, SpecIF:InstantiationUser

## DDP:InspectionCharacteristicUsesInspectionResource (SpecIF:TermStatementClass)
- SpecIF:LocalTerm: (InspectionCharacteristic) Uses (InspectionResource)
- SpecIF:TermStatus: SpecIF:LifecycleStatusReleased
- SpecIF:Domain: SpecIF:DomainSystemsEngineering
- SpecIF:Instantiation: SpecIF:InstantiationAuto, SpecIF:InstantiationUser

## DDP:InspectionPlanPartOfInspectionPlan (SpecIF:TermStatementClass)
- dcterms:description: Superior element
- SpecIF:LocalTerm: (InspectionPlan) PartOf (InspectionPlan)
- SpecIF:TermStatus: SpecIF:LifecycleStatusReleased
- SpecIF:Domain: SpecIF:DomainSystemsEngineering
- SpecIF:Instantiation: SpecIF:InstantiationAuto, SpecIF:InstantiationUser

## DDP:InspectionPlanRelatesToRevision (SpecIF:TermStatementClass)
- dcterms:description: Relation to a version
- SpecIF:LocalTerm: (InspectionPlan) RelatesTo (Revision)
- SpecIF:TermStatus: SpecIF:LifecycleStatusReleased
- SpecIF:Domain: SpecIF:DomainSystemsEngineering
- SpecIF:Instantiation: SpecIF:InstantiationAuto, SpecIF:InstantiationUser

## DDP:InspectionResourcePartOfInspectionResource (SpecIF:TermStatementClass)
- dcterms:description: Superior element
- SpecIF:LocalTerm: (InspectionResource) PartOf (InspectionResource)
- SpecIF:TermStatus: SpecIF:LifecycleStatusReleased
- SpecIF:Domain: SpecIF:DomainSystemsEngineering
- SpecIF:Instantiation: SpecIF:InstantiationAuto, SpecIF:InstantiationUser

## DDP:InspectionResourceSpecialismOfInspectionResource (SpecIF:TermStatementClass)
- dcterms:description: More generic item
- SpecIF:LocalTerm: (InspectionResource) SpecialismOf (InspectionResource)
- SpecIF:TermStatus: SpecIF:LifecycleStatusReleased
- SpecIF:Domain: SpecIF:DomainSystemsEngineering
- SpecIF:Instantiation: SpecIF:InstantiationAuto, SpecIF:InstantiationUser

## DDP:InspectionResourceRelatesToRevision (SpecIF:TermStatementClass)
- dcterms:description: Relation to a version
- SpecIF:LocalTerm: (InspectionResource) RelatesTo (Revision)
- SpecIF:TermStatus: SpecIF:LifecycleStatusReleased
- SpecIF:Domain: SpecIF:DomainSystemsEngineering
- SpecIF:Instantiation: SpecIF:InstantiationAuto, SpecIF:InstantiationUser

## DDP:InspectionResourceRelatesToConfiguration (SpecIF:TermStatementClass)
- dcterms:description: Relation to a configuration
- SpecIF:LocalTerm: (InspectionResource) RelatesTo (Configuration)
- SpecIF:TermStatus: SpecIF:LifecycleStatusReleased
- SpecIF:Domain: SpecIF:DomainSystemsEngineering
- SpecIF:Instantiation: SpecIF:InstantiationAuto, SpecIF:InstantiationUser

## DDP:InspectionResourceOwnedByPerson (SpecIF:TermStatementClass)
- dcterms:description: The role owning this use case
- SpecIF:LocalTerm: (InspectionResource) OwnedBy (Person)
- SpecIF:TermStatus: SpecIF:LifecycleStatusReleased
- SpecIF:Domain: SpecIF:DomainSystemsEngineering
- SpecIF:Instantiation: SpecIF:InstantiationAuto, SpecIF:InstantiationUser

## DDP:InspectionResourceImplementsProductFunction (SpecIF:TermStatementClass)
- dcterms:description: Function implemented by the component
- SpecIF:LocalTerm: (InspectionResource) Implements (ProductFunction)
- SpecIF:TermStatus: SpecIF:LifecycleStatusReleased
- SpecIF:Domain: SpecIF:DomainSystemsEngineering
- SpecIF:Instantiation: SpecIF:InstantiationAuto, SpecIF:InstantiationUser

## DDP:InspectionResourceFulfilsRequirement (SpecIF:TermStatementClass)
- dcterms:description: Requirement implemented by the component. According to systems engineering best-practice, a requirement should first be answered by a function, and the function will be implemented by a component. This direct relation should therefore only be used if no functions have been defined.
- SpecIF:LocalTerm: (InspectionResource) Fulfils (Requirement)
- SpecIF:TermStatus: SpecIF:LifecycleStatusReleased
- SpecIF:Domain: SpecIF:DomainSystemsEngineering
- SpecIF:Instantiation: SpecIF:InstantiationAuto, SpecIF:InstantiationUser

## DDP:InspectionRunUsesInspectionPlan (SpecIF:TermStatementClass)
- SpecIF:LocalTerm: (InspectionRun) Uses (InspectionPlan)
- SpecIF:TermStatus: SpecIF:LifecycleStatusReleased
- SpecIF:Domain: SpecIF:DomainSystemsEngineering
- SpecIF:Instantiation: SpecIF:InstantiationAuto, SpecIF:InstantiationUser

## DDP:InspectionResultPartOfInspectionResult (SpecIF:TermStatementClass)
- dcterms:description: Superior element
- SpecIF:LocalTerm: (InspectionResult) PartOf (InspectionResult)
- SpecIF:TermStatus: SpecIF:LifecycleStatusReleased
- SpecIF:Domain: SpecIF:DomainSystemsEngineering
- SpecIF:Instantiation: SpecIF:InstantiationAuto, SpecIF:InstantiationUser

## DDP:InspectionResultRelatesToRevision (SpecIF:TermStatementClass)
- dcterms:description: Relation to a version
- SpecIF:LocalTerm: (InspectionResult) RelatesTo (Revision)
- SpecIF:TermStatus: SpecIF:LifecycleStatusReleased
- SpecIF:Domain: SpecIF:DomainSystemsEngineering
- SpecIF:Instantiation: SpecIF:InstantiationAuto, SpecIF:InstantiationUser

## DDP:InspectionResultResultFromInspectionRun (SpecIF:TermStatementClass)
- dcterms:description: Inspection run that created this inspection result
- SpecIF:LocalTerm: (InspectionResult) ResultFrom (InspectionRun)
- SpecIF:TermStatus: SpecIF:LifecycleStatusReleased
- SpecIF:Domain: SpecIF:DomainSystemsEngineering
- SpecIF:Instantiation: SpecIF:InstantiationAuto, SpecIF:InstantiationUser

## Property Class Terms (SpecIF:Heading)
- dcterms:description: A property carries information 'payload' and may be applied to resources or statements. The SpecIF terms listed in this chapter are used as property name/title, whereas the information is provided as 'value'. Usually a combination of complimentary properties is used per resource or statement class.
  A property corresponds to an 'ATTRIBUTE-DEFINITION' resp. 'ATTRIBUTE-VALUE' in the Requirements Interchange Format (ReqIF).

## dc:identifier (SpecIF:TermPropertyClassString)
- dcterms:description: Represents a configuration as a context for other elements to be valid. The datamodel allows selected elements to be related to a revision, i. e. mechanical components
- SpecIF:TermStatus: SpecIF:LifecycleStatusReleased
- SpecIF:Domain: SpecIF:DomainSystemsEngineering

## DDP:number (SpecIF:TermPropertyClassString)
- dcterms:description: Represents a configuration as a context for other elements to be valid. The datamodel allows selected elements to be related to a revision, i. e. mechanical components
- SpecIF:LocalTerm: number
- SpecIF:TermStatus: SpecIF:LifecycleStatusReleased
- SpecIF:Domain: SpecIF:DomainSystemsEngineering

## dc:title (SpecIF:TermPropertyClassString)
- dcterms:description: Represents a configuration as a context for other elements to be valid. The datamodel allows selected elements to be related to a revision, i. e. mechanical components
- SpecIF:TermStatus: SpecIF:LifecycleStatusReleased
- SpecIF:Domain: SpecIF:DomainSystemsEngineering

## dc:description (SpecIF:TermPropertyClassString)
- dcterms:description: Represents a configuration as a context for other elements to be valid. The datamodel allows selected elements to be related to a revision, i. e. mechanical components
- SpecIF:TermStatus: SpecIF:LifecycleStatusReleased
- SpecIF:Domain: SpecIF:DomainSystemsEngineering

## DDP:customAttribute (SpecIF:TermPropertyClassString)
- dcterms:description: Represents a configuration as a context for other elements to be valid. The datamodel allows selected elements to be related to a revision, i. e. mechanical components
- SpecIF:LocalTerm: customAttribute
- SpecIF:TermStatus: SpecIF:LifecycleStatusReleased
- SpecIF:Domain: SpecIF:DomainSystemsEngineering

## DDP:title (SpecIF:TermPropertyClassString)
- dcterms:description: Represents a real person, but may also be a system user that appears in source data. The FOAF (Friend of a Friend) Ontology has been considered, but is not used as it does not provide a structured representation for firstname, lastname and title of a person.
- SpecIF:LocalTerm: title
- SpecIF:TermStatus: SpecIF:LifecycleStatusReleased
- SpecIF:Domain: SpecIF:DomainSystemsEngineering

## DDP:firstname (SpecIF:TermPropertyClassString)
- dcterms:description: Represents a real person, but may also be a system user that appears in source data. The FOAF (Friend of a Friend) Ontology has been considered, but is not used as it does not provide a structured representation for firstname, lastname and title of a person.
- SpecIF:LocalTerm: firstname
- SpecIF:TermStatus: SpecIF:LifecycleStatusReleased
- SpecIF:Domain: SpecIF:DomainSystemsEngineering

## DDP:lastname (SpecIF:TermPropertyClassString)
- dcterms:description: Represents a real person, but may also be a system user that appears in source data. The FOAF (Friend of a Friend) Ontology has been considered, but is not used as it does not provide a structured representation for firstname, lastname and title of a person.
- SpecIF:LocalTerm: lastname
- SpecIF:TermStatus: SpecIF:LifecycleStatusReleased
- SpecIF:Domain: SpecIF:DomainSystemsEngineering

## DDP:mail (SpecIF:TermPropertyClassString)
- dcterms:description: Represents a real person, but may also be a system user that appears in source data. The FOAF (Friend of a Friend) Ontology has been considered, but is not used as it does not provide a structured representation for firstname, lastname and title of a person.
- SpecIF:LocalTerm: mail
- SpecIF:TermStatus: SpecIF:LifecycleStatusReleased
- SpecIF:Domain: SpecIF:DomainSystemsEngineering

## DDP:phone (SpecIF:TermPropertyClassString)
- dcterms:description: Represents a real person, but may also be a system user that appears in source data. The FOAF (Friend of a Friend) Ontology has been considered, but is not used as it does not provide a structured representation for firstname, lastname and title of a person.
- SpecIF:LocalTerm: phone
- SpecIF:TermStatus: SpecIF:LifecycleStatusReleased
- SpecIF:Domain: SpecIF:DomainSystemsEngineering

## DDP:startDateTime (SpecIF:TermPropertyClassTimestamp)
- dcterms:description: Represents a revision as a context for other elements to be valid. The datamodel allows selected elements to be related to a revision, i. e. mechanical components.
- SpecIF:LocalTerm: startDateTime
- SpecIF:TermStatus: SpecIF:LifecycleStatusReleased
- SpecIF:Domain: SpecIF:DomainSystemsEngineering

## DDP:endDateTime (SpecIF:TermPropertyClassTimestamp)
- dcterms:description: Represents a revision as a context for other elements to be valid. The datamodel allows selected elements to be related to a revision, i. e. mechanical components.
- SpecIF:LocalTerm: endDateTime
- SpecIF:TermStatus: SpecIF:LifecycleStatusReleased
- SpecIF:Domain: SpecIF:DomainSystemsEngineering

## DDP:costCenter (SpecIF:TermPropertyClassString)
- dcterms:description: Represents a project or sub-project
- SpecIF:LocalTerm: costCenter
- SpecIF:TermStatus: SpecIF:LifecycleStatusReleased
- SpecIF:Domain: SpecIF:DomainSystemsEngineering

## DDP:type (SpecIF:TermPropertyClassString)
- dcterms:description: Represents a revision as a context for other elements to be valid. The datamodel allows selected elements to be related to a revision, i. e. mechanical components.
- SpecIF:LocalTerm: type
- SpecIF:TermStatus: SpecIF:LifecycleStatusReleased
- SpecIF:Domain: SpecIF:DomainSystemsEngineering

## DDP:mass (SpecIF:TermPropertyClassReal)
- dcterms:description: Represents all kinds of tools and equipment used to manufacture parts and assemble the product.
- SpecIF:LocalTerm: mass
- SpecIF:TermStatus: SpecIF:LifecycleStatusReleased
- SpecIF:Domain: SpecIF:DomainSystemsEngineering

## DDP:toleranceType (SpecIF:TermPropertyClassString)
- dcterms:description: A text annotation, dimension, tolerance, surface specification, etc. with relation to product geometry
- SpecIF:LocalTerm: toleranceType
- SpecIF:TermStatus: SpecIF:LifecycleStatusReleased
- SpecIF:Domain: SpecIF:DomainSystemsEngineering

## DDP:nominalValue (SpecIF:TermPropertyClassReal)
- dcterms:description: A text annotation, dimension, tolerance, surface specification, etc. with relation to product geometry
- SpecIF:LocalTerm: nominalValue
- SpecIF:TermStatus: SpecIF:LifecycleStatusReleased
- SpecIF:Domain: SpecIF:DomainSystemsEngineering

## DDP:upperTolerance (SpecIF:TermPropertyClassReal)
- dcterms:description: A text annotation, dimension, tolerance, surface specification, etc. with relation to product geometry
- SpecIF:LocalTerm: upperTolerance
- SpecIF:TermStatus: SpecIF:LifecycleStatusReleased
- SpecIF:Domain: SpecIF:DomainSystemsEngineering

## DDP:lowerTolerance (SpecIF:TermPropertyClassReal)
- dcterms:description: A text annotation, dimension, tolerance, surface specification, etc. with relation to product geometry
- SpecIF:LocalTerm: lowerTolerance
- SpecIF:TermStatus: SpecIF:LifecycleStatusReleased
- SpecIF:Domain: SpecIF:DomainSystemsEngineering

## DDP:classification (SpecIF:TermPropertyClassString)
- dcterms:description: A text annotation, dimension, tolerance, surface specification, etc. with relation to product geometry
- SpecIF:LocalTerm: classification
- SpecIF:TermStatus: SpecIF:LifecycleStatusReleased
- SpecIF:Domain: SpecIF:DomainSystemsEngineering

## DDP:coating (SpecIF:TermPropertyClassString)
- dcterms:description: A text annotation, dimension, tolerance, surface specification, etc. with relation to product geometry
- SpecIF:LocalTerm: coating
- SpecIF:TermStatus: SpecIF:LifecycleStatusReleased
- SpecIF:Domain: SpecIF:DomainSystemsEngineering

## DDP:comment (SpecIF:TermPropertyClassString)
- dcterms:description: A text annotation, dimension, tolerance, surface specification, etc. with relation to product geometry
- SpecIF:LocalTerm: comment
- SpecIF:TermStatus: SpecIF:LifecycleStatusReleased
- SpecIF:Domain: SpecIF:DomainSystemsEngineering

## DDP:side (SpecIF:TermPropertyClassString)
- dcterms:description: Represents a joining element such as a welding spot, a rivet, etc.
- SpecIF:LocalTerm: side
- SpecIF:TermStatus: SpecIF:LifecycleStatusReleased
- SpecIF:Domain: SpecIF:DomainSystemsEngineering

## Property Value Terms (SpecIF:Heading)
- dcterms:description: These are terms for certain enumerated property values. Not only the property titles, but also any enumerated value must be mapped between different systems or domains; therefore using defined terms is beneficial. Of course, like any other vocabulary term, a term used as property value for transmission or storage can be translated for display.

## Statements
- DDP:Role SpecIF:hasProperty dc:identifier
- DDP:Role SpecIF:hasProperty DDP:number
- DDP:Role SpecIF:hasProperty dc:title
- DDP:Role SpecIF:hasProperty dc:description
- DDP:Role SpecIF:hasProperty DDP:customAttribute
- DDP:Person SpecIF:hasProperty dc:identifier
- DDP:Person SpecIF:hasProperty DDP:title
- DDP:Person SpecIF:hasProperty DDP:firstname
- DDP:Person SpecIF:hasProperty DDP:lastname
- DDP:Person SpecIF:hasProperty DDP:mail
- DDP:Person SpecIF:hasProperty DDP:phone
- DDP:Person SpecIF:hasProperty DDP:customAttribute
- DDP:OrganizationUnit SpecIF:hasProperty dc:identifier
- DDP:OrganizationUnit SpecIF:hasProperty DDP:number
- DDP:OrganizationUnit SpecIF:hasProperty dc:title
- DDP:OrganizationUnit SpecIF:hasProperty dc:description
- DDP:OrganizationUnit SpecIF:hasProperty DDP:customAttribute
- DDP:Task SpecIF:hasProperty dc:identifier
- DDP:Task SpecIF:hasProperty DDP:number
- DDP:Task SpecIF:hasProperty dc:title
- DDP:Task SpecIF:hasProperty dc:description
- DDP:Task SpecIF:hasProperty DDP:startDateTime
- DDP:Task SpecIF:hasProperty DDP:endDateTime
- DDP:Task SpecIF:hasProperty DDP:customAttribute
- DDP:Project SpecIF:hasProperty dc:identifier
- DDP:Project SpecIF:hasProperty DDP:number
- DDP:Project SpecIF:hasProperty dc:title
- DDP:Project SpecIF:hasProperty dc:description
- DDP:Project SpecIF:hasProperty DDP:startDateTime
- DDP:Project SpecIF:hasProperty DDP:endDateTime
- DDP:Project SpecIF:hasProperty DDP:costCenter
- DDP:Project SpecIF:hasProperty DDP:customAttribute
- DDP:UseCase SpecIF:hasProperty dc:identifier
- DDP:UseCase SpecIF:hasProperty DDP:number
- DDP:UseCase SpecIF:hasProperty dc:title
- DDP:UseCase SpecIF:hasProperty dc:description
- DDP:UseCase SpecIF:hasProperty DDP:customAttribute
- DDP:Requirement SpecIF:hasProperty dc:identifier
- DDP:Requirement SpecIF:hasProperty DDP:number
- DDP:Requirement SpecIF:hasProperty dc:title
- DDP:Requirement SpecIF:hasProperty dc:description
- DDP:Requirement SpecIF:hasProperty DDP:type
- DDP:Requirement SpecIF:hasProperty DDP:customAttribute
- DDP:ProductFunction SpecIF:hasProperty dc:identifier
- DDP:ProductFunction SpecIF:hasProperty DDP:number
- DDP:ProductFunction SpecIF:hasProperty dc:title
- DDP:ProductFunction SpecIF:hasProperty dc:description
- DDP:ProductFunction SpecIF:hasProperty DDP:type
- DDP:ProductFunction SpecIF:hasProperty DDP:customAttribute
- DDP:SystemComponent SpecIF:hasProperty dc:identifier
- DDP:SystemComponent SpecIF:hasProperty DDP:number
- DDP:SystemComponent SpecIF:hasProperty dc:title
- DDP:SystemComponent SpecIF:hasProperty dc:description
- DDP:SystemComponent SpecIF:hasProperty DDP:type
- DDP:SystemComponent SpecIF:hasProperty DDP:customAttribute
- DDP:ComponentInterface SpecIF:hasProperty dc:identifier
- DDP:ComponentInterface SpecIF:hasProperty DDP:number
- DDP:ComponentInterface SpecIF:hasProperty dc:title
- DDP:ComponentInterface SpecIF:hasProperty dc:description
- DDP:ComponentInterface SpecIF:hasProperty DDP:customAttribute
- DDP:ComponentConnection SpecIF:hasProperty dc:identifier
- DDP:ComponentConnection SpecIF:hasProperty DDP:number
- DDP:ComponentConnection SpecIF:hasProperty dc:title
- DDP:ComponentConnection SpecIF:hasProperty dc:description
- DDP:ComponentConnection SpecIF:hasProperty DDP:type
- DDP:ComponentConnection SpecIF:hasProperty DDP:customAttribute
- DDP:ComponentState SpecIF:hasProperty dc:identifier
- DDP:ComponentState SpecIF:hasProperty DDP:number
- DDP:ComponentState SpecIF:hasProperty dc:title
- DDP:ComponentState SpecIF:hasProperty dc:description
- DDP:ComponentState SpecIF:hasProperty DDP:customAttribute
- DDP:MechanicalComponent SpecIF:hasProperty dc:identifier
- DDP:MechanicalComponent SpecIF:hasProperty DDP:number
- DDP:MechanicalComponent SpecIF:hasProperty dc:title
- DDP:MechanicalComponent SpecIF:hasProperty dc:description
- DDP:MechanicalComponent SpecIF:hasProperty DDP:type
- DDP:MechanicalComponent SpecIF:hasProperty DDP:mass
- DDP:MechanicalComponent SpecIF:hasProperty DDP:customAttribute
- DDP:MechanicalComponentInstance SpecIF:hasProperty dc:identifier
- DDP:MechanicalComponentInstance SpecIF:hasProperty DDP:number
- DDP:MechanicalComponentInstance SpecIF:hasProperty dc:title
- DDP:MechanicalComponentInstance SpecIF:hasProperty dc:description
- DDP:MechanicalComponentInstance SpecIF:hasProperty DDP:customAttribute
- DDP:Material SpecIF:hasProperty dc:identifier
- DDP:Material SpecIF:hasProperty DDP:number
- DDP:Material SpecIF:hasProperty dc:title
- DDP:Material SpecIF:hasProperty dc:description
- DDP:Material SpecIF:hasProperty DDP:type
- DDP:Material SpecIF:hasProperty DDP:customAttribute
- DDP:ModelView SpecIF:hasProperty dc:identifier
- DDP:ModelView SpecIF:hasProperty dc:title
- DDP:ModelView SpecIF:hasProperty dc:description
- DDP:ModelView SpecIF:hasProperty DDP:type
- DDP:ModelView SpecIF:hasProperty DDP:customAttribute
- DDP:ModelAnnotation SpecIF:hasProperty dc:identifier
- DDP:ModelAnnotation SpecIF:hasProperty dc:title
- DDP:ModelAnnotation SpecIF:hasProperty dc:description
- DDP:ModelAnnotation SpecIF:hasProperty DDP:type
- DDP:ModelAnnotation SpecIF:hasProperty DDP:toleranceType
- DDP:ModelAnnotation SpecIF:hasProperty DDP:nominalValue
- DDP:ModelAnnotation SpecIF:hasProperty DDP:upperTolerance
- DDP:ModelAnnotation SpecIF:hasProperty DDP:lowerTolerance
- DDP:ModelAnnotation SpecIF:hasProperty DDP:classification
- DDP:ModelAnnotation SpecIF:hasProperty DDP:coating
- DDP:ModelAnnotation SpecIF:hasProperty DDP:comment
- DDP:ModelAnnotation SpecIF:hasProperty DDP:customAttribute
- DDP:KinematicMechanism SpecIF:hasProperty dc:identifier
- DDP:KinematicMechanism SpecIF:hasProperty dc:title
- DDP:KinematicMechanism SpecIF:hasProperty dc:description
- DDP:KinematicMechanism SpecIF:hasProperty DDP:customAttribute
- DDP:KinematicJoint SpecIF:hasProperty dc:identifier
- DDP:KinematicJoint SpecIF:hasProperty DDP:number
- DDP:KinematicJoint SpecIF:hasProperty dc:title
- DDP:KinematicJoint SpecIF:hasProperty dc:description
- DDP:KinematicJoint SpecIF:hasProperty DDP:type
- DDP:KinematicJoint SpecIF:hasProperty DDP:customAttribute
- DDP:KinematicSensor SpecIF:hasProperty dc:identifier
- DDP:KinematicSensor SpecIF:hasProperty dc:title
- DDP:KinematicSensor SpecIF:hasProperty dc:description
- DDP:KinematicSensor SpecIF:hasProperty DDP:type
- DDP:KinematicSensor SpecIF:hasProperty DDP:customAttribute
- DDP:KinematicMotion SpecIF:hasProperty dc:identifier
- DDP:KinematicMotion SpecIF:hasProperty dc:title
- DDP:KinematicMotion SpecIF:hasProperty dc:description
- DDP:KinematicMotion SpecIF:hasProperty DDP:customAttribute
- DDP:JoiningProcess SpecIF:hasProperty dc:identifier
- DDP:JoiningProcess SpecIF:hasProperty dc:title
- DDP:JoiningProcess SpecIF:hasProperty dc:description
- DDP:JoiningProcess SpecIF:hasProperty DDP:customAttribute
- DDP:JoiningElement SpecIF:hasProperty dc:identifier
- DDP:JoiningElement SpecIF:hasProperty DDP:number
- DDP:JoiningElement SpecIF:hasProperty dc:title
- DDP:JoiningElement SpecIF:hasProperty dc:description
- DDP:JoiningElement SpecIF:hasProperty DDP:type
- DDP:JoiningElement SpecIF:hasProperty DDP:side
- DDP:JoiningElement SpecIF:hasProperty DDP:customAttribute
- DDP:ElectricElectronicComponent SpecIF:hasProperty dc:identifier
- DDP:ElectricElectronicComponent SpecIF:hasProperty DDP:number
- DDP:ElectricElectronicComponent SpecIF:hasProperty dc:title
- DDP:ElectricElectronicComponent SpecIF:hasProperty dc:description
- DDP:ElectricElectronicComponent SpecIF:hasProperty DDP:type
- DDP:ElectricElectronicComponent SpecIF:hasProperty DDP:customAttribute
- DDP:ElectricElectronicPort SpecIF:hasProperty dc:identifier
- DDP:ElectricElectronicPort SpecIF:hasProperty DDP:number
- DDP:ElectricElectronicPort SpecIF:hasProperty dc:title
- DDP:ElectricElectronicPort SpecIF:hasProperty dc:description
- DDP:ElectricElectronicPort SpecIF:hasProperty DDP:customAttribute
- DDP:ElectricElectronicConnection SpecIF:hasProperty dc:identifier
- DDP:ElectricElectronicConnection SpecIF:hasProperty DDP:number
- DDP:ElectricElectronicConnection SpecIF:hasProperty dc:title
- DDP:ElectricElectronicConnection SpecIF:hasProperty dc:description
- DDP:ElectricElectronicConnection SpecIF:hasProperty DDP:type
- DDP:ElectricElectronicConnection SpecIF:hasProperty DDP:customAttribute
- DDP:SoftwareClass SpecIF:hasProperty dc:identifier
- DDP:SoftwareClass SpecIF:hasProperty DDP:number
- DDP:SoftwareClass SpecIF:hasProperty dc:title
- DDP:SoftwareClass SpecIF:hasProperty dc:description
- DDP:SoftwareClass SpecIF:hasProperty DDP:type
- DDP:SoftwareClass SpecIF:hasProperty DDP:customAttribute
- DDP:SoftwareInterface SpecIF:hasProperty dc:identifier
- DDP:SoftwareInterface SpecIF:hasProperty DDP:number
- DDP:SoftwareInterface SpecIF:hasProperty dc:title
- DDP:SoftwareInterface SpecIF:hasProperty dc:description
- DDP:SoftwareInterface SpecIF:hasProperty DDP:customAttribute
- DDP:SoftwareComponent SpecIF:hasProperty dc:identifier
- DDP:SoftwareComponent SpecIF:hasProperty DDP:number
- DDP:SoftwareComponent SpecIF:hasProperty dc:title
- DDP:SoftwareComponent SpecIF:hasProperty dc:description
- DDP:SoftwareComponent SpecIF:hasProperty DDP:type
- DDP:SoftwareComponent SpecIF:hasProperty DDP:customAttribute
- DDP:HydraulicPneumaticConnection SpecIF:hasProperty dc:identifier
- DDP:HydraulicPneumaticConnection SpecIF:hasProperty DDP:number
- DDP:HydraulicPneumaticConnection SpecIF:hasProperty dc:title
- DDP:HydraulicPneumaticConnection SpecIF:hasProperty dc:description
- DDP:HydraulicPneumaticConnection SpecIF:hasProperty DDP:customAttribute
- DDP:HydraulicPneumaticPort SpecIF:hasProperty dc:identifier
- DDP:HydraulicPneumaticPort SpecIF:hasProperty DDP:number
- DDP:HydraulicPneumaticPort SpecIF:hasProperty dc:title
- DDP:HydraulicPneumaticPort SpecIF:hasProperty dc:description
- DDP:HydraulicPneumaticPort SpecIF:hasProperty DDP:customAttribute
- DDP:ValidationPlan SpecIF:hasProperty dc:identifier
- DDP:ValidationPlan SpecIF:hasProperty dc:title
- DDP:ValidationPlan SpecIF:hasProperty dc:description
- DDP:ValidationPlan SpecIF:hasProperty DDP:type
- DDP:ValidationPlan SpecIF:hasProperty DDP:customAttribute
- DDP:ValidationBoundaryCondition SpecIF:hasProperty dc:identifier
- DDP:ValidationBoundaryCondition SpecIF:hasProperty dc:title
- DDP:ValidationBoundaryCondition SpecIF:hasProperty dc:description
- DDP:ValidationBoundaryCondition SpecIF:hasProperty DDP:type
- DDP:ValidationBoundaryCondition SpecIF:hasProperty DDP:customAttribute
- DDP:ValidationRun SpecIF:hasProperty dc:identifier
- DDP:ValidationRun SpecIF:hasProperty dc:title
- DDP:ValidationRun SpecIF:hasProperty dc:description
- DDP:ValidationRun SpecIF:hasProperty DDP:type
- DDP:ValidationRun SpecIF:hasProperty DDP:startDateTime
- DDP:ValidationRun SpecIF:hasProperty DDP:endDateTime
- DDP:ValidationRun SpecIF:hasProperty DDP:customAttribute
- DDP:ValidationResult SpecIF:hasProperty dc:identifier
- DDP:ValidationResult SpecIF:hasProperty dc:title
- DDP:ValidationResult SpecIF:hasProperty dc:description
- DDP:ValidationResult SpecIF:hasProperty DDP:type
- DDP:ValidationResult SpecIF:hasProperty DDP:customAttribute
- DDP:ManufacturingOperation SpecIF:hasProperty dc:identifier
- DDP:ManufacturingOperation SpecIF:hasProperty DDP:number
- DDP:ManufacturingOperation SpecIF:hasProperty dc:title
- DDP:ManufacturingOperation SpecIF:hasProperty dc:description
- DDP:ManufacturingOperation SpecIF:hasProperty DDP:type
- DDP:ManufacturingOperation SpecIF:hasProperty DDP:customAttribute
- DDP:ManufacturingEquipmentComponent SpecIF:hasProperty dc:identifier
- DDP:ManufacturingEquipmentComponent SpecIF:hasProperty DDP:number
- DDP:ManufacturingEquipmentComponent SpecIF:hasProperty dc:title
- DDP:ManufacturingEquipmentComponent SpecIF:hasProperty dc:description
- DDP:ManufacturingEquipmentComponent SpecIF:hasProperty DDP:type
- DDP:ManufacturingEquipmentComponent SpecIF:hasProperty DDP:mass
- DDP:ManufacturingEquipmentComponent SpecIF:hasProperty DDP:customAttribute
- DDP:InspectionCharacteristic SpecIF:hasProperty dc:identifier
- DDP:InspectionCharacteristic SpecIF:hasProperty DDP:number
- DDP:InspectionCharacteristic SpecIF:hasProperty dc:title
- DDP:InspectionCharacteristic SpecIF:hasProperty dc:description
- DDP:InspectionCharacteristic SpecIF:hasProperty DDP:type
- DDP:InspectionCharacteristic SpecIF:hasProperty DDP:customAttribute
- DDP:InspectionPlan SpecIF:hasProperty dc:identifier
- DDP:InspectionPlan SpecIF:hasProperty DDP:number
- DDP:InspectionPlan SpecIF:hasProperty dc:title
- DDP:InspectionPlan SpecIF:hasProperty dc:description
- DDP:InspectionPlan SpecIF:hasProperty DDP:type
- DDP:InspectionPlan SpecIF:hasProperty DDP:customAttribute
- DDP:InspectionResource SpecIF:hasProperty dc:identifier
- DDP:InspectionResource SpecIF:hasProperty DDP:number
- DDP:InspectionResource SpecIF:hasProperty dc:title
- DDP:InspectionResource SpecIF:hasProperty dc:description
- DDP:InspectionResource SpecIF:hasProperty DDP:type
- DDP:InspectionResource SpecIF:hasProperty DDP:customAttribute
- DDP:InspectionRun SpecIF:hasProperty dc:identifier
- DDP:InspectionRun SpecIF:hasProperty DDP:number
- DDP:InspectionRun SpecIF:hasProperty dc:title
- DDP:InspectionRun SpecIF:hasProperty dc:description
- DDP:InspectionRun SpecIF:hasProperty DDP:startDateTime
- DDP:InspectionRun SpecIF:hasProperty DDP:endDateTime
- DDP:InspectionRun SpecIF:hasProperty DDP:customAttribute
- DDP:InspectionResult SpecIF:hasProperty dc:identifier
- DDP:InspectionResult SpecIF:hasProperty DDP:number
- DDP:InspectionResult SpecIF:hasProperty dc:title
- DDP:InspectionResult SpecIF:hasProperty dc:description
- DDP:InspectionResult SpecIF:hasProperty DDP:type
- DDP:InspectionResult SpecIF:hasProperty DDP:customAttribute
- DDP:Revision SpecIF:hasProperty dc:identifier
- DDP:Revision SpecIF:hasProperty DDP:number
- DDP:Revision SpecIF:hasProperty dc:title
- DDP:Revision SpecIF:hasProperty dc:description
- DDP:Revision SpecIF:hasProperty DDP:startDateTime
- DDP:Revision SpecIF:hasProperty DDP:endDateTime
- DDP:Revision SpecIF:hasProperty DDP:type
- DDP:Revision SpecIF:hasProperty DDP:customAttribute
- DDP:Configuration SpecIF:hasProperty dc:identifier
- DDP:Configuration SpecIF:hasProperty DDP:number
- DDP:Configuration SpecIF:hasProperty dc:title
- DDP:Configuration SpecIF:hasProperty dc:description
- DDP:Configuration SpecIF:hasProperty DDP:customAttribute
- DDP:Role SpecIF:isEligibleAsSubject DDP:RolePartOfRole
- DDP:Role SpecIF:isEligibleAsObject DDP:RolePartOfRole
- DDP:Role SpecIF:isEligibleAsSubject DDP:RoleSpecialismOfRole
- DDP:Role SpecIF:isEligibleAsObject DDP:RoleSpecialismOfRole
- DDP:Person SpecIF:isEligibleAsSubject DDP:PersonMemberOfOrganizationUnit
- DDP:OrganizationUnit SpecIF:isEligibleAsObject DDP:PersonMemberOfOrganizationUnit
- DDP:OrganizationUnit SpecIF:isEligibleAsSubject DDP:OrganizationUnitPartOfOrganizationUnit
- DDP:OrganizationUnit SpecIF:isEligibleAsObject DDP:OrganizationUnitPartOfOrganizationUnit
- DDP:Task SpecIF:isEligibleAsSubject DDP:TaskPartOfTask
- DDP:Task SpecIF:isEligibleAsObject DDP:TaskPartOfTask
- DDP:Task SpecIF:isEligibleAsSubject DDP:TaskCreatedByPerson
- DDP:Person SpecIF:isEligibleAsObject DDP:TaskCreatedByPerson
- DDP:Task SpecIF:isEligibleAsSubject DDP:TaskAssignedToPerson
- DDP:Person SpecIF:isEligibleAsObject DDP:TaskAssignedToPerson
- DDP:Task SpecIF:isEligibleAsSubject DDP:TaskConductedByOrganizationUnit
- DDP:OrganizationUnit SpecIF:isEligibleAsObject DDP:TaskConductedByOrganizationUnit
- DDP:Project SpecIF:isEligibleAsSubject DDP:ProjectPartOfProject
- DDP:Project SpecIF:isEligibleAsObject DDP:ProjectPartOfProject
- DDP:Project SpecIF:isEligibleAsSubject DDP:ProjectCreatedByPerson
- DDP:Person SpecIF:isEligibleAsObject DDP:ProjectCreatedByPerson
- DDP:Project SpecIF:isEligibleAsSubject DDP:ProjectAssignedToPerson
- DDP:Person SpecIF:isEligibleAsObject DDP:ProjectAssignedToPerson
- DDP:Project SpecIF:isEligibleAsSubject DDP:ProjectConductedByOrganizationUnit
- DDP:OrganizationUnit SpecIF:isEligibleAsObject DDP:ProjectConductedByOrganizationUnit
- DDP:UseCase SpecIF:isEligibleAsSubject DDP:UseCasePartOfUseCase
- DDP:UseCase SpecIF:isEligibleAsObject DDP:UseCasePartOfUseCase
- DDP:UseCase SpecIF:isEligibleAsSubject DDP:UseCaseSpecialismOfUseCase
- DDP:UseCase SpecIF:isEligibleAsObject DDP:UseCaseSpecialismOfUseCase
- DDP:UseCase SpecIF:isEligibleAsSubject DDP:UseCaseRelatesToConfiguration
- DDP:Configuration SpecIF:isEligibleAsObject DDP:UseCaseRelatesToConfiguration
- DDP:UseCase SpecIF:isEligibleAsSubject DDP:UseCaseOwnedByPerson
- DDP:Person SpecIF:isEligibleAsObject DDP:UseCaseOwnedByPerson
- DDP:UseCase SpecIF:isEligibleAsSubject DDP:UseCaseAbstractionOfUseCase
- DDP:UseCase SpecIF:isEligibleAsObject DDP:UseCaseAbstractionOfUseCase
- DDP:UseCase SpecIF:isEligibleAsSubject DDP:UseCaseCreatedByPerson
- DDP:Person SpecIF:isEligibleAsObject DDP:UseCaseCreatedByPerson
- DDP:Requirement SpecIF:isEligibleAsSubject DDP:RequirementPartOfRequirement
- DDP:Requirement SpecIF:isEligibleAsObject DDP:RequirementPartOfRequirement
- DDP:Requirement SpecIF:isEligibleAsSubject DDP:RequirementSpecialismOfRequirement
- DDP:Requirement SpecIF:isEligibleAsObject DDP:RequirementSpecialismOfRequirement
- DDP:Requirement SpecIF:isEligibleAsSubject DDP:RequirementRelatesToRevision
- DDP:Revision SpecIF:isEligibleAsObject DDP:RequirementRelatesToRevision
- DDP:Requirement SpecIF:isEligibleAsSubject DDP:RequirementRelatesToConfiguration
- DDP:Configuration SpecIF:isEligibleAsObject DDP:RequirementRelatesToConfiguration
- DDP:Requirement SpecIF:isEligibleAsSubject DDP:RequirementCreatedByPerson
- DDP:Person SpecIF:isEligibleAsObject DDP:RequirementCreatedByPerson
- DDP:Requirement SpecIF:isEligibleAsSubject DDP:RequirementRelatedToSystemComponent
- DDP:SystemComponent SpecIF:isEligibleAsObject DDP:RequirementRelatedToSystemComponent
- DDP:ProductFunction SpecIF:isEligibleAsSubject DDP:ProductFunctionPartOfProductFunction
- DDP:ProductFunction SpecIF:isEligibleAsObject DDP:ProductFunctionPartOfProductFunction
- DDP:ProductFunction SpecIF:isEligibleAsSubject DDP:ProductFunctionSpecialismOfProductFunction
- DDP:ProductFunction SpecIF:isEligibleAsObject DDP:ProductFunctionSpecialismOfProductFunction
- DDP:ProductFunction SpecIF:isEligibleAsSubject DDP:ProductFunctionRelatesToRevision
- DDP:Revision SpecIF:isEligibleAsObject DDP:ProductFunctionRelatesToRevision
- DDP:ProductFunction SpecIF:isEligibleAsSubject DDP:ProductFunctionRelatesToConfiguration
- DDP:Configuration SpecIF:isEligibleAsObject DDP:ProductFunctionRelatesToConfiguration
- DDP:ProductFunction SpecIF:isEligibleAsSubject DDP:ProductFunctionFollowsProductFunction
- DDP:ProductFunction SpecIF:isEligibleAsObject DDP:ProductFunctionFollowsProductFunction
- DDP:ProductFunction SpecIF:isEligibleAsSubject DDP:ProductFunctionFulfilsRequirement
- DDP:Requirement SpecIF:isEligibleAsObject DDP:ProductFunctionFulfilsRequirement
- DDP:SystemComponent SpecIF:isEligibleAsSubject DDP:SystemComponentPartOfSystemComponent
- DDP:SystemComponent SpecIF:isEligibleAsObject DDP:SystemComponentPartOfSystemComponent
- DDP:SystemComponent SpecIF:isEligibleAsSubject DDP:SystemComponentSpecialismOfSystemComponent
- DDP:SystemComponent SpecIF:isEligibleAsObject DDP:SystemComponentSpecialismOfSystemComponent
- DDP:SystemComponent SpecIF:isEligibleAsSubject DDP:SystemComponentRelatesToRevision
- DDP:Revision SpecIF:isEligibleAsObject DDP:SystemComponentRelatesToRevision
- DDP:SystemComponent SpecIF:isEligibleAsSubject DDP:SystemComponentRelatesToConfiguration
- DDP:Configuration SpecIF:isEligibleAsObject DDP:SystemComponentRelatesToConfiguration
- DDP:SystemComponent SpecIF:isEligibleAsSubject DDP:SystemComponentOwnedByPerson
- DDP:Person SpecIF:isEligibleAsObject DDP:SystemComponentOwnedByPerson
- DDP:SystemComponent SpecIF:isEligibleAsSubject DDP:SystemComponentImplementsProductFunction
- DDP:ProductFunction SpecIF:isEligibleAsObject DDP:SystemComponentImplementsProductFunction
- DDP:SystemComponent SpecIF:isEligibleAsSubject DDP:SystemComponentFulfilsRequirement
- DDP:Requirement SpecIF:isEligibleAsObject DDP:SystemComponentFulfilsRequirement
- DDP:ComponentInterface SpecIF:isEligibleAsSubject DDP:ComponentInterfaceAllocatedToSystemComponent
- DDP:SystemComponent SpecIF:isEligibleAsObject DDP:ComponentInterfaceAllocatedToSystemComponent
- DDP:ComponentConnection SpecIF:isEligibleAsSubject DDP:ComponentConnectionRelatesToConfiguration
- DDP:Configuration SpecIF:isEligibleAsObject DDP:ComponentConnectionRelatesToConfiguration
- DDP:ComponentConnection SpecIF:isEligibleAsSubject DDP:ComponentConnectionConnectsSystemComponent
- DDP:SystemComponent SpecIF:isEligibleAsObject DDP:ComponentConnectionConnectsSystemComponent
- DDP:ComponentState SpecIF:isEligibleAsSubject DDP:ComponentStatePartOfComponentState
- DDP:ComponentState SpecIF:isEligibleAsObject DDP:ComponentStatePartOfComponentState
- DDP:ComponentState SpecIF:isEligibleAsSubject DDP:ComponentStateAllocatedToSystemComponent
- DDP:SystemComponent SpecIF:isEligibleAsObject DDP:ComponentStateAllocatedToSystemComponent
- DDP:ComponentState SpecIF:isEligibleAsSubject DDP:ComponentStateChangesToComponentState
- DDP:ComponentState SpecIF:isEligibleAsObject DDP:ComponentStateChangesToComponentState
- DDP:MechanicalComponent SpecIF:isEligibleAsSubject DDP:MechanicalComponentPartOfMechanicalComponent
- DDP:MechanicalComponent SpecIF:isEligibleAsObject DDP:MechanicalComponentPartOfMechanicalComponent
- DDP:MechanicalComponent SpecIF:isEligibleAsSubject DDP:MechanicalComponentSpecialismOfMechanicalComponent
- DDP:MechanicalComponent SpecIF:isEligibleAsObject DDP:MechanicalComponentSpecialismOfMechanicalComponent
- DDP:MechanicalComponent SpecIF:isEligibleAsSubject DDP:MechanicalComponentRelatesToRevision
- DDP:Revision SpecIF:isEligibleAsObject DDP:MechanicalComponentRelatesToRevision
- DDP:MechanicalComponent SpecIF:isEligibleAsSubject DDP:MechanicalComponentRelatesToConfiguration
- DDP:Configuration SpecIF:isEligibleAsObject DDP:MechanicalComponentRelatesToConfiguration
- DDP:MechanicalComponent SpecIF:isEligibleAsSubject DDP:MechanicalComponentOwnedByPerson
- DDP:Person SpecIF:isEligibleAsObject DDP:MechanicalComponentOwnedByPerson
- DDP:MechanicalComponent SpecIF:isEligibleAsSubject DDP:MechanicalComponentImplementsProductFunction
- DDP:ProductFunction SpecIF:isEligibleAsObject DDP:MechanicalComponentImplementsProductFunction
- DDP:MechanicalComponent SpecIF:isEligibleAsSubject DDP:MechanicalComponentFulfilsRequirement
- DDP:Requirement SpecIF:isEligibleAsObject DDP:MechanicalComponentFulfilsRequirement
- DDP:MechanicalComponent SpecIF:isEligibleAsSubject DDP:MechanicalComponentMadeOfMaterial
- DDP:Material SpecIF:isEligibleAsObject DDP:MechanicalComponentMadeOfMaterial
- DDP:MechanicalComponentInstance SpecIF:isEligibleAsSubject DDP:MechanicalComponentInstanceAllocatedToMechanicalComponent
- DDP:MechanicalComponent SpecIF:isEligibleAsObject DDP:MechanicalComponentInstanceAllocatedToMechanicalComponent
- DDP:MechanicalComponentInstance SpecIF:isEligibleAsSubject DDP:MechanicalComponentInstanceInstancesMechanicalComponent
- DDP:MechanicalComponent SpecIF:isEligibleAsObject DDP:MechanicalComponentInstanceInstancesMechanicalComponent
- DDP:Material SpecIF:isEligibleAsSubject DDP:MaterialSpecialismOfMaterial
- DDP:Material SpecIF:isEligibleAsObject DDP:MaterialSpecialismOfMaterial
- DDP:ModelView SpecIF:isEligibleAsSubject DDP:ModelViewRelatesToConfiguration
- DDP:Configuration SpecIF:isEligibleAsObject DDP:ModelViewRelatesToConfiguration
- DDP:ModelView SpecIF:isEligibleAsSubject DDP:ModelViewAllocatedToMechanicalComponent
- DDP:MechanicalComponent SpecIF:isEligibleAsObject DDP:ModelViewAllocatedToMechanicalComponent
- DDP:ModelAnnotation SpecIF:isEligibleAsSubject DDP:ModelAnnotationAllocatedToModelView
- DDP:ModelView SpecIF:isEligibleAsObject DDP:ModelAnnotationAllocatedToModelView
- DDP:ModelAnnotation SpecIF:isEligibleAsSubject DDP:ModelAnnotationRelatesToModelAnnotation
- DDP:ModelAnnotation SpecIF:isEligibleAsObject DDP:ModelAnnotationRelatesToModelAnnotation
- DDP:KinematicMechanism SpecIF:isEligibleAsSubject DDP:KinematicMechanismAllocatedToMechanicalComponent
- DDP:MechanicalComponent SpecIF:isEligibleAsObject DDP:KinematicMechanismAllocatedToMechanicalComponent
- DDP:KinematicJoint SpecIF:isEligibleAsSubject DDP:KinematicJointRelatesToConfiguration
- DDP:Configuration SpecIF:isEligibleAsObject DDP:KinematicJointRelatesToConfiguration
- DDP:KinematicJoint SpecIF:isEligibleAsSubject DDP:KinematicJointConnectsSystemComponent
- DDP:SystemComponent SpecIF:isEligibleAsObject DDP:KinematicJointConnectsSystemComponent
- DDP:KinematicJoint SpecIF:isEligibleAsSubject DDP:KinematicJointConnectsMechanicalComponent
- DDP:MechanicalComponent SpecIF:isEligibleAsObject DDP:KinematicJointConnectsMechanicalComponent
- DDP:KinematicJoint SpecIF:isEligibleAsSubject DDP:KinematicJointAllocatedToKinematicMechanism
- DDP:KinematicMechanism SpecIF:isEligibleAsObject DDP:KinematicJointAllocatedToKinematicMechanism
- DDP:KinematicJoint SpecIF:isEligibleAsSubject DDP:KinematicJointObservedByKinematicSensor
- DDP:KinematicSensor SpecIF:isEligibleAsObject DDP:KinematicJointObservedByKinematicSensor
- DDP:KinematicSensor SpecIF:isEligibleAsSubject DDP:KinematicSensorAllocatedToKinematicMechanism
- DDP:KinematicMechanism SpecIF:isEligibleAsObject DDP:KinematicSensorAllocatedToKinematicMechanism
- DDP:KinematicMotion SpecIF:isEligibleAsSubject DDP:KinematicMotionInvolvesMechanicalComponent
- DDP:MechanicalComponent SpecIF:isEligibleAsObject DDP:KinematicMotionInvolvesMechanicalComponent
- DDP:JoiningProcess SpecIF:isEligibleAsSubject DDP:JoiningProcessSpecialismOfJoiningProcess
- DDP:JoiningProcess SpecIF:isEligibleAsObject DDP:JoiningProcessSpecialismOfJoiningProcess
- DDP:JoiningElement SpecIF:isEligibleAsSubject DDP:JoiningElementRelatesToConfiguration
- DDP:Configuration SpecIF:isEligibleAsObject DDP:JoiningElementRelatesToConfiguration
- DDP:JoiningElement SpecIF:isEligibleAsSubject DDP:JoiningElementConnectsSystemComponent
- DDP:SystemComponent SpecIF:isEligibleAsObject DDP:JoiningElementConnectsSystemComponent
- DDP:JoiningElement SpecIF:isEligibleAsSubject DDP:JoiningElementConnectsMechanicalComponentInstance
- DDP:MechanicalComponentInstance SpecIF:isEligibleAsObject DDP:JoiningElementConnectsMechanicalComponentInstance
- DDP:JoiningElement SpecIF:isEligibleAsSubject DDP:JoiningElementAllocatedToMechanicalComponent
- DDP:MechanicalComponent SpecIF:isEligibleAsObject DDP:JoiningElementAllocatedToMechanicalComponent
- DDP:JoiningElement SpecIF:isEligibleAsSubject DDP:JoiningElementAppliesJoiningProcess
- DDP:JoiningProcess SpecIF:isEligibleAsObject DDP:JoiningElementAppliesJoiningProcess
- DDP:ElectricElectronicComponent SpecIF:isEligibleAsSubject DDP:ElectricElectronicComponentPartOfElectricElectronicComponent
- DDP:ElectricElectronicComponent SpecIF:isEligibleAsObject DDP:ElectricElectronicComponentPartOfElectricElectronicComponent
- DDP:ElectricElectronicComponent SpecIF:isEligibleAsSubject DDP:ElectricElectronicComponentSpecialismOfElectricElectronicComponent
- DDP:ElectricElectronicComponent SpecIF:isEligibleAsObject DDP:ElectricElectronicComponentSpecialismOfElectricElectronicComponent
- DDP:ElectricElectronicComponent SpecIF:isEligibleAsSubject DDP:ElectricElectronicComponentRelatesToRevision
- DDP:Revision SpecIF:isEligibleAsObject DDP:ElectricElectronicComponentRelatesToRevision
- DDP:ElectricElectronicComponent SpecIF:isEligibleAsSubject DDP:ElectricElectronicComponentRelatesToConfiguration
- DDP:Configuration SpecIF:isEligibleAsObject DDP:ElectricElectronicComponentRelatesToConfiguration
- DDP:ElectricElectronicComponent SpecIF:isEligibleAsSubject DDP:ElectricElectronicComponentOwnedByPerson
- DDP:Person SpecIF:isEligibleAsObject DDP:ElectricElectronicComponentOwnedByPerson
- DDP:ElectricElectronicComponent SpecIF:isEligibleAsSubject DDP:ElectricElectronicComponentImplementsProductFunction
- DDP:ProductFunction SpecIF:isEligibleAsObject DDP:ElectricElectronicComponentImplementsProductFunction
- DDP:ElectricElectronicComponent SpecIF:isEligibleAsSubject DDP:ElectricElectronicComponentFulfilsRequirement
- DDP:Requirement SpecIF:isEligibleAsObject DDP:ElectricElectronicComponentFulfilsRequirement
- DDP:ElectricElectronicComponent SpecIF:isEligibleAsSubject DDP:ElectricElectronicComponentRelatesToMechanicalComponent
- DDP:MechanicalComponent SpecIF:isEligibleAsObject DDP:ElectricElectronicComponentRelatesToMechanicalComponent
- DDP:ElectricElectronicPort SpecIF:isEligibleAsSubject DDP:ElectricElectronicPortAllocatedToSystemComponent
- DDP:SystemComponent SpecIF:isEligibleAsObject DDP:ElectricElectronicPortAllocatedToSystemComponent
- DDP:ElectricElectronicConnection SpecIF:isEligibleAsSubject DDP:ElectricElectronicConnectionRelatesToConfiguration
- DDP:Configuration SpecIF:isEligibleAsObject DDP:ElectricElectronicConnectionRelatesToConfiguration
- DDP:ElectricElectronicConnection SpecIF:isEligibleAsSubject DDP:ElectricElectronicConnectionConnectsSystemComponent
- DDP:SystemComponent SpecIF:isEligibleAsObject DDP:ElectricElectronicConnectionConnectsSystemComponent
- DDP:ElectricElectronicConnection SpecIF:isEligibleAsSubject DDP:ElectricElectronicConnectionConnectsElectricElectronicComponent
- DDP:ElectricElectronicComponent SpecIF:isEligibleAsObject DDP:ElectricElectronicConnectionConnectsElectricElectronicComponent
- DDP:SoftwareClass SpecIF:isEligibleAsSubject DDP:SoftwareClassPartOfSoftwareClass
- DDP:SoftwareClass SpecIF:isEligibleAsObject DDP:SoftwareClassPartOfSoftwareClass
- DDP:SoftwareClass SpecIF:isEligibleAsSubject DDP:SoftwareClassSpecialismOfSoftwareClass
- DDP:SoftwareClass SpecIF:isEligibleAsObject DDP:SoftwareClassSpecialismOfSoftwareClass
- DDP:SoftwareClass SpecIF:isEligibleAsSubject DDP:SoftwareClassRelatesToRevision
- DDP:Revision SpecIF:isEligibleAsObject DDP:SoftwareClassRelatesToRevision
- DDP:SoftwareClass SpecIF:isEligibleAsSubject DDP:SoftwareClassRelatesToConfiguration
- DDP:Configuration SpecIF:isEligibleAsObject DDP:SoftwareClassRelatesToConfiguration
- DDP:SoftwareClass SpecIF:isEligibleAsSubject DDP:SoftwareClassOwnedByPerson
- DDP:Person SpecIF:isEligibleAsObject DDP:SoftwareClassOwnedByPerson
- DDP:SoftwareClass SpecIF:isEligibleAsSubject DDP:SoftwareClassImplementsProductFunction
- DDP:ProductFunction SpecIF:isEligibleAsObject DDP:SoftwareClassImplementsProductFunction
- DDP:SoftwareClass SpecIF:isEligibleAsSubject DDP:SoftwareClassFulfilsRequirement
- DDP:Requirement SpecIF:isEligibleAsObject DDP:SoftwareClassFulfilsRequirement
- DDP:SoftwareInterface SpecIF:isEligibleAsSubject DDP:SoftwareInterfaceAllocatedToSystemComponent
- DDP:SystemComponent SpecIF:isEligibleAsObject DDP:SoftwareInterfaceAllocatedToSystemComponent
- DDP:SoftwareInterface SpecIF:isEligibleAsSubject DDP:SoftwareInterfaceAllocatedToSoftwareComponent
- DDP:SoftwareComponent SpecIF:isEligibleAsObject DDP:SoftwareInterfaceAllocatedToSoftwareComponent
- DDP:SoftwareComponent SpecIF:isEligibleAsSubject DDP:SoftwareComponentPartOfSoftwareComponent
- DDP:SoftwareComponent SpecIF:isEligibleAsObject DDP:SoftwareComponentPartOfSoftwareComponent
- DDP:SoftwareComponent SpecIF:isEligibleAsSubject DDP:SoftwareComponentSpecialismOfSoftwareComponent
- DDP:SoftwareComponent SpecIF:isEligibleAsObject DDP:SoftwareComponentSpecialismOfSoftwareComponent
- DDP:SoftwareComponent SpecIF:isEligibleAsSubject DDP:SoftwareComponentRelatesToRevision
- DDP:Revision SpecIF:isEligibleAsObject DDP:SoftwareComponentRelatesToRevision
- DDP:SoftwareComponent SpecIF:isEligibleAsSubject DDP:SoftwareComponentRelatesToConfiguration
- DDP:Configuration SpecIF:isEligibleAsObject DDP:SoftwareComponentRelatesToConfiguration
- DDP:SoftwareComponent SpecIF:isEligibleAsSubject DDP:SoftwareComponentOwnedByPerson
- DDP:Person SpecIF:isEligibleAsObject DDP:SoftwareComponentOwnedByPerson
- DDP:SoftwareComponent SpecIF:isEligibleAsSubject DDP:SoftwareComponentImplementsProductFunction
- DDP:ProductFunction SpecIF:isEligibleAsObject DDP:SoftwareComponentImplementsProductFunction
- DDP:SoftwareComponent SpecIF:isEligibleAsSubject DDP:SoftwareComponentFulfilsRequirement
- DDP:Requirement SpecIF:isEligibleAsObject DDP:SoftwareComponentFulfilsRequirement
- DDP:HydraulicPneumaticPort SpecIF:isEligibleAsSubject DDP:HydraulicPneumaticPortAllocatedToSystemComponent
- DDP:SystemComponent SpecIF:isEligibleAsObject DDP:HydraulicPneumaticPortAllocatedToSystemComponent
- DDP:ValidationPlan SpecIF:isEligibleAsSubject DDP:ValidationPlanPartOfValidationPlan
- DDP:ValidationPlan SpecIF:isEligibleAsObject DDP:ValidationPlanPartOfValidationPlan
- DDP:ValidationBoundaryCondition SpecIF:isEligibleAsSubject DDP:ValidationBoundaryConditionPartOfValidationBoundaryCondition
- DDP:ValidationBoundaryCondition SpecIF:isEligibleAsObject DDP:ValidationBoundaryConditionPartOfValidationBoundaryCondition
- DDP:ValidationRun SpecIF:isEligibleAsSubject DDP:ValidationRunPartOfValidationRun
- DDP:ValidationRun SpecIF:isEligibleAsObject DDP:ValidationRunPartOfValidationRun
- DDP:ValidationResult SpecIF:isEligibleAsSubject DDP:ValidationResultPartOfValidationResult
- DDP:ValidationResult SpecIF:isEligibleAsObject DDP:ValidationResultPartOfValidationResult
- DDP:ManufacturingOperation SpecIF:isEligibleAsSubject DDP:ManufacturingOperationPartOfManufacturingOperation
- DDP:ManufacturingOperation SpecIF:isEligibleAsObject DDP:ManufacturingOperationPartOfManufacturingOperation
- DDP:ManufacturingOperation SpecIF:isEligibleAsSubject DDP:ManufacturingOperationInContextOfMechanicalComponent
- DDP:MechanicalComponent SpecIF:isEligibleAsObject DDP:ManufacturingOperationInContextOfMechanicalComponent
- DDP:ManufacturingOperation SpecIF:isEligibleAsSubject DDP:ManufacturingOperationAppliesToMechanicalComponentInstance
- DDP:MechanicalComponentInstance SpecIF:isEligibleAsObject DDP:ManufacturingOperationAppliesToMechanicalComponentInstance
- DDP:ManufacturingOperation SpecIF:isEligibleAsSubject DDP:ManufacturingOperationPerformedUsingManufacturingEquipmentComponent
- DDP:ManufacturingEquipmentComponent SpecIF:isEligibleAsObject DDP:ManufacturingOperationPerformedUsingManufacturingEquipmentComponent
- DDP:ManufacturingEquipmentComponent SpecIF:isEligibleAsSubject DDP:ManufacturingEquipmentComponentPartOfManufacturingEquipmentComponent
- DDP:ManufacturingEquipmentComponent SpecIF:isEligibleAsObject DDP:ManufacturingEquipmentComponentPartOfManufacturingEquipmentComponent
- DDP:ManufacturingEquipmentComponent SpecIF:isEligibleAsSubject DDP:ManufacturingEquipmentComponentSpecialismOfManufacturingEquipmentComponent
- DDP:ManufacturingEquipmentComponent SpecIF:isEligibleAsObject DDP:ManufacturingEquipmentComponentSpecialismOfManufacturingEquipmentComponent
- DDP:ManufacturingEquipmentComponent SpecIF:isEligibleAsSubject DDP:ManufacturingEquipmentComponentRelatesToRevision
- DDP:Revision SpecIF:isEligibleAsObject DDP:ManufacturingEquipmentComponentRelatesToRevision
- DDP:ManufacturingEquipmentComponent SpecIF:isEligibleAsSubject DDP:ManufacturingEquipmentComponentRelatesToConfiguration
- DDP:Configuration SpecIF:isEligibleAsObject DDP:ManufacturingEquipmentComponentRelatesToConfiguration
- DDP:ManufacturingEquipmentComponent SpecIF:isEligibleAsSubject DDP:ManufacturingEquipmentComponentOwnedByPerson
- DDP:Person SpecIF:isEligibleAsObject DDP:ManufacturingEquipmentComponentOwnedByPerson
- DDP:ManufacturingEquipmentComponent SpecIF:isEligibleAsSubject DDP:ManufacturingEquipmentComponentImplementsProductFunction
- DDP:ProductFunction SpecIF:isEligibleAsObject DDP:ManufacturingEquipmentComponentImplementsProductFunction
- DDP:ManufacturingEquipmentComponent SpecIF:isEligibleAsSubject DDP:ManufacturingEquipmentComponentFulfilsRequirement
- DDP:Requirement SpecIF:isEligibleAsObject DDP:ManufacturingEquipmentComponentFulfilsRequirement
- DDP:ManufacturingEquipmentComponent SpecIF:isEligibleAsSubject DDP:ManufacturingEquipmentComponentMadeOfMaterial
- DDP:Material SpecIF:isEligibleAsObject DDP:ManufacturingEquipmentComponentMadeOfMaterial
- DDP:InspectionCharacteristic SpecIF:isEligibleAsSubject DDP:InspectionCharacteristicPartOfInspectionCharacteristic
- DDP:InspectionCharacteristic SpecIF:isEligibleAsObject DDP:InspectionCharacteristicPartOfInspectionCharacteristic
- DDP:InspectionCharacteristic SpecIF:isEligibleAsSubject DDP:InspectionCharacteristicAllocatedToInspectionPlan
- DDP:InspectionPlan SpecIF:isEligibleAsObject DDP:InspectionCharacteristicAllocatedToInspectionPlan
- DDP:InspectionCharacteristic SpecIF:isEligibleAsSubject DDP:InspectionCharacteristicValidatesProductFunction
- DDP:ProductFunction SpecIF:isEligibleAsObject DDP:InspectionCharacteristicValidatesProductFunction
- DDP:InspectionCharacteristic SpecIF:isEligibleAsSubject DDP:InspectionCharacteristicUsesInspectionResource
- DDP:InspectionResource SpecIF:isEligibleAsObject DDP:InspectionCharacteristicUsesInspectionResource
- DDP:InspectionPlan SpecIF:isEligibleAsSubject DDP:InspectionPlanPartOfInspectionPlan
- DDP:InspectionPlan SpecIF:isEligibleAsObject DDP:InspectionPlanPartOfInspectionPlan
- DDP:InspectionPlan SpecIF:isEligibleAsSubject DDP:InspectionPlanRelatesToRevision
- DDP:Revision SpecIF:isEligibleAsObject DDP:InspectionPlanRelatesToRevision
- DDP:InspectionResource SpecIF:isEligibleAsSubject DDP:InspectionResourcePartOfInspectionResource
- DDP:InspectionResource SpecIF:isEligibleAsObject DDP:InspectionResourcePartOfInspectionResource
- DDP:InspectionResource SpecIF:isEligibleAsSubject DDP:InspectionResourceSpecialismOfInspectionResource
- DDP:InspectionResource SpecIF:isEligibleAsObject DDP:InspectionResourceSpecialismOfInspectionResource
- DDP:InspectionResource SpecIF:isEligibleAsSubject DDP:InspectionResourceRelatesToRevision
- DDP:Revision SpecIF:isEligibleAsObject DDP:InspectionResourceRelatesToRevision
- DDP:InspectionResource SpecIF:isEligibleAsSubject DDP:InspectionResourceRelatesToConfiguration
- DDP:Configuration SpecIF:isEligibleAsObject DDP:InspectionResourceRelatesToConfiguration
- DDP:InspectionResource SpecIF:isEligibleAsSubject DDP:InspectionResourceOwnedByPerson
- DDP:Person SpecIF:isEligibleAsObject DDP:InspectionResourceOwnedByPerson
- DDP:InspectionResource SpecIF:isEligibleAsSubject DDP:InspectionResourceImplementsProductFunction
- DDP:ProductFunction SpecIF:isEligibleAsObject DDP:InspectionResourceImplementsProductFunction
- DDP:InspectionResource SpecIF:isEligibleAsSubject DDP:InspectionResourceFulfilsRequirement
- DDP:Requirement SpecIF:isEligibleAsObject DDP:InspectionResourceFulfilsRequirement
- DDP:InspectionRun SpecIF:isEligibleAsSubject DDP:InspectionRunUsesInspectionPlan
- DDP:InspectionPlan SpecIF:isEligibleAsObject DDP:InspectionRunUsesInspectionPlan
- DDP:InspectionResult SpecIF:isEligibleAsSubject DDP:InspectionResultPartOfInspectionResult
- DDP:InspectionResult SpecIF:isEligibleAsObject DDP:InspectionResultPartOfInspectionResult
- DDP:InspectionResult SpecIF:isEligibleAsSubject DDP:InspectionResultRelatesToRevision
- DDP:Revision SpecIF:isEligibleAsObject DDP:InspectionResultRelatesToRevision
- DDP:InspectionResult SpecIF:isEligibleAsSubject DDP:InspectionResultResultFromInspectionRun
- DDP:InspectionRun SpecIF:isEligibleAsObject DDP:InspectionResultResultFromInspectionRun

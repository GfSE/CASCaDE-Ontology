# SpecIF Classes with tiny example CRM
A set of SpecIF Classes derived from a SpecIF Ontology for the domains SpecIF:DomainRequirementsEngineering, SpecIF:DomainSystemsEngineering, SpecIF:DomainSystemModelIntegration, SpecIF:DomainEnterpriseArchitecture with tiny example CRM.
- Rights: Creative Commons 4.0 CC BY-SA, https://creativecommons.org/licenses/by-sa/4.0/

## Customer Relationship Management (CRM) (DDP:ProductFunction)
- dcterms:description: The app The app provide the ability to create, read, update and delete customers with their
  - contact person (full name)*
  - postal address
  - e-mail address*
  - telephone number
  - bank account

## App manages customers (IREB:Requirement)
- dcterms:description: The app MUST provide the ability to create, read, update and delete customer information.
- SpecIF:Priority: SpecIF:priorityRatherHigh
- IREB:RequirementType: SpecIF:Feature
- SpecIF:StakeholderGroup: SpecIF:StakeholderGroupBusiness

## Statements
- Customer Relationship Management (CRM) oslc_rm:satisfies App manages customers
